---1202v04
--*********************************************************************
-- Filename:    1202v04.MIB
-- Description: This MIB defines the Actuated Signal Controller (ASC) Objects
--              and includes 1217v0135e.MIB, which is used in conjunction with
--              SAE data elements.
-- Source:      NTCIP 1202 v4.06b
-- MIB Revision History:
-- Date:       January 20, 2025
--
-- Copyright 2025 by the American Association of State Highway and
-- Transportation Officials (AASHTO), the Institute of Transportation
-- Engineers (ITE), and the National Electrical Manufacturers Association
-- (NEMA). All intellectual property rights, including, but not limited to,
-- the rights of reproduction in whole or in part in any form, translation
-- into other languages and display are reserved by the copyright owners 
-- under the laws of the United States of America, the Universal Copyright
-- Convention, the Berne Convention, and the International and Pan American
-- Copyright Conventions. Except for the MIB, Do not copy without written 
-- permission of either AASHTO, ITE, or NEMA.
-- 
--                     Joint NEMA, AASHTO, and ITE
--                  NTCIP Management Information Base
--                        DISTRIBUTION NOTICE
-- 
--You may make or distribute unlimited copies, including derivative works,
--of the DD or MIB, including copies for commercial distribution, provided
--that:
-- 
--a) each copy you make or distribute includes the citation "Derived from
--NTCIP 1202 v04. Copyright by AASHTO / ITE / NEMA. Used by permission.",
-- or this header;
--b) the copies or derivative works are not made part of the standard
--publications or works offered by other standard developing organizations
--or publishers or as works-for-hire not associated with commercial hardware
--or software products intended for field implementation;
--c) use of the DD or MIB is restricted in that the syntax fields may only
--be modified to define: 1) a more restrictive subrange; or 2) a subset of
--the standard enumerated values; or 3) a set of retired and defined
--enumerated values for systems supporting multiversion interoperability;
--d) the description field may be modified but only to the extent that:
--1) the more restrictive subrange is defined; and 2) only those bit values
--or enumerated values that are supported are listed; and
--e) each derivative work of the MIB uses the same module name followed
--by "-", followed by your Internet Assigned Number Authority (IANA)-assigned
--enterprise number or other identifier.
--
--These materials are delivered "AS IS" without any warranties as to their
--use or performance.-- 
-- These materials are delivered "AS IS" without any warranties as to their
-- use or performance.
-- 
-- AASHTO/ITE/NEMA AND THEIR SUPPLIERS DO NOT WARRANT THE PERFORMANCE OR
-- RESULTS YOU MAY OBTAIN BY USING THESE MATERIALS. AASHTO/ITE/NEMA AND THEIR
-- SUPPLIERS MAKE NO WARRANTIES, EXPRESS OR IMPLIED, AS TO NONINFRINGEMENT OF
-- THIRD PARTY RIGHTS, MERCHANTABILITY, OR FITNESS FOR ANY PARTICULAR
-- PURPOSE.
-- IN NO EVENT WILL AASHTO, ITE OR NEMA OR THEIR SUPPLIERS BE LIABLE TO YOU
-- OR ANY THIRD PARTY FOR ANY CLAIM OR FOR ANY CONSEQUENTIAL, INCIDENTAL OR
-- SPECIAL DAMAGES, INCLUDING ANY LOST PROFITS OR LOST SAVINGS, ARISING FROM
-- YOUR REPRODUCTION OR USE OF THESE MATERIALS, EVEN IF AN AASHTO, ITE, OR
-- NEMA REPRESENTATIVE HAS BEEN ADVISED OF THE POSSIBILITY OF SUCH DAMAGES.
-- Some states or jurisdictions do not allow the exclusion or limitation of
-- incidental, consequential or special damages, or the exclusion of implied
-- warranties, so the above limitations may not apply to you.
-- 
-- Use of these materials does not constitute an endorsement or affiliation
-- by or between AASHTO, ITE, or NEMA and you, your company, or your
-- products and services.
-- 
-- NTCIP is a trademark of AASHTO/ITE/NEMA.
--**************************************************************************

--
-- ***** TEMPORARY NOTE *****
-- simpleweb.org test compile include files:

--  NTCIP8004-Transportation.mib
--  NTICP8004-NEMA.mib
--  RFC1213-MIB-Modified.txt    <- added range to ifIndex
--  ISO26048-1-FieldDevice-TC.mib

--
-- Questions are flagged with: "v04 check"
-- ***** TEMPORARY NOTE *****
--


-- 5.1 MIB Header
NTCIP1202-v04 DEFINITIONS ::= BEGIN


-- the following OBJECT IDENTIFIERS are used in the ASC MIB:
IMPORTS
    OBJECT-TYPE                             FROM RFC-1212

    DisplayString, ifIndex                  FROM RFC1213-MIB-Modified
    SnmpAdminString
                                            FROM SNMP-FRAMEWORK-MIB
                                            -- RFC 3411
    zeroDotZero                             FROM SNMPv2-SMI
    ITSOerString                            FROM ISO26048-1-FieldDevice-TC
    devices                                 FROM NTCIP8004-Transportation

--I think OwnerString is replaced with SnmpAdminString? 
--The 8004 mib replaces it with NtcipOwnerString but its deprecated. I'm not sure we need it
--I think SMI v2 replaces null with zerodotzero from RFC2578? It seems we only use null for Object Identifiers
-- Oerstring seems to be replaced by ITSOerString from the FieldDevice-TC mib?


    MODULE-IDENTITY, OBJECT-TYPE, OBJECT-IDENTITY,
    Integer32, Unsigned32, IpAddress, Counter32  FROM SNMPv2-SMI 

                                            -- RFC 2578
    RowStatus, StorageType, VariablePointer
                                            FROM SNMPv2-TC
                                            -- RFC 2579
    MODULE-COMPLIANCE, OBJECT-GROUP
                                            FROM SNMPv2-CONF
                                            -- RFC 2580

;


-- ****************************************************************************
-- Administrative Objects
-- ****************************************************************************
asc MODULE-IDENTITY
  LAST-UPDATED "202501201000Z"

  ORGANIZATION "NTCIP ASC WG"
  CONTACT-INFO
   "name: NTCIP Coordinator
    email: ntcip@nema.org
    postal:  National Electrical Manufacturers Association
             1300 North 17th Street, Suite 1752
             Rosslyn, VA 22209-3801
             USA"
  DESCRIPTION
  "<Definition> This MIB defines the structure of management information
    under the asc node, which is used to manage Actuated Signal
    Controllers (ASC) Objects.
  <Object Identifier> 1.3.6.1.4.1.1206.4.2.1"
  REVISION "202501201000Z"
  DESCRIPTION "NTCIP 1202 v04 - Change to SMIv2"
  REVISION "202309190500Z"
  DESCRIPTION "NTCIP 1202 v0335 - Last update"
  ::= { devices 1 }

--5.2 Phase Parameters
phase OBJECT-IDENTITY
    STATUS current
    DESCRIPTION  "<Definition> Phase parameters.
        for ASC traffic controllers.
    <Object Identifier> 1.3.6.1.4.1.1206.4.2.1.1"
    ::= { asc 1 }

-- This node shall contain objects that configure, monitor or 
-- control phase functions for this device.

--5.2.1 Maximum Phases
maxPhases OBJECT-TYPE
    SYNTAX Integer32 (2..255)
    UNITS "phase"
    MAX-ACCESS read-only
    STATUS current
    DESCRIPTION  "<Definition> The Maximum Number of Phases this Controller
        Unit supports. This object indicates the maximum rows which shall
        appear in the phaseTable object.
    <Object Identifier> 1.3.6.1.4.1.1206.4.2.1.1.1
    <Object Type> S"
    ::= { phase 1 }

--5.2.2 Phase Table
phaseTable OBJECT-TYPE
    SYNTAX SEQUENCE OF PhaseEntry
    MAX-ACCESS not-accessible
    STATUS current
    DESCRIPTION "<Definition> A table containing Controller Unit phase
        parameters. The number of rows in this table is equal to the
        maxPhases object.

        The objects in this table correspond to the matching objects in the
        first set (phaseSetNumber = 1) of the phaseSetTable.
    <TableType> static
    <Object Identifier> 1.3.6.1.4.1.1206.4.2.1.1.2"
    ::= { phase 2 }

phaseEntry OBJECT-TYPE
    SYNTAX PhaseEntry
    MAX-ACCESS not-accessible
    STATUS current
    DESCRIPTION "<Definition> Parameters for a specific Controller Unit phase.
    <Object Identifier> 1.3.6.1.4.1.1206.4.2.1.1.2.1"
    INDEX { phaseNumber }
    ::= { phaseTable 1 }
 
PhaseEntry ::= SEQUENCE { 
    phaseNumber                     Integer32,
    phaseWalk                       Integer32,
    phasePedestrianClear            Integer32,
    phaseMinimumGreen               Integer32,
    phasePassage                    Integer32,
    phaseMaximum1                   Integer32,
    phaseMaximum2                   Integer32,
    phaseYellowChange               Integer32,
    phaseRedClear                   Integer32,
    phaseRedRevert                  Integer32,
    phaseAddedInitial               Integer32,
    phaseMaximumInitial             Integer32,
    phaseTimeBeforeReduction        Integer32,
    phaseCarsBeforeReduction        Integer32,
    phaseTimeToReduce               Integer32,
    phaseReduceBy                   Integer32,
    phaseMinimumGap                 Integer32,
    phaseDynamicMaxLimit            Integer32,
    phaseDynamicMaxStep             Integer32,
    phaseStartup                    INTEGER,
    phaseOptions                    Integer32,
    phaseRing                       Integer32,
    phaseConcurrency                OCTET STRING,
    phaseMaximum3                   Integer32,
    phasePedClearDuringVehicleClear Integer32,
    phasePedServiceLimit            Integer32,
    phaseDontWalkRevert             Integer32,
    phasePedAlternateClearance      Integer32,
    phasePedAlternateWalk           Integer32,
    phasePedAdvanceWalkTime         Integer32, 
    phasePedDelayTime               Integer32, 
    phaseAdvWarnGrnStartTime        Integer32,
    phaseAdvWarnRedStartTime        Integer32,
    phaseAltMinTimeTransition       Integer32,
    phaseWalkDuringTransition       Integer32,
    phasePedClearDuringTransition   Integer32    }

--5.2.2.1   Phase Number
phaseNumber OBJECT-TYPE
    SYNTAX Integer32 (1..255)
    UNITS "phase"
    MAX-ACCESS not-accessible
    STATUS current
    DESCRIPTION "<Definition> The phase number for objects in this row. This
        value shall not exceed the maxPhases object value.
    <Object Identifier> 1.3.6.1.4.1.1206.4.2.1.1.2.1.1"
    ::= { phaseEntry 1 }

--5.2.2.2   Phase Walk Parameter
phaseWalk OBJECT-TYPE
    SYNTAX Integer32 (0..255)
    UNITS "second"
    MAX-ACCESS read-write
    STATUS current
    DESCRIPTION "<Definition> Phase Walk Parameter in seconds. This shall
        control the amount of time the WALK indication shall be displayed.
        This parameter shall be used regardless whether the pedestrian
        indication associated with this phase is for a ped-only phase or for
        a pedestrian indication that runs parallel to a vehicle phase.
    <Object Identifier> 1.3.6.1.4.1.1206.4.2.1.1.2.1.2
    <Object Type> P"
    REFERENCE "NEMA TS 2 Clause 3.5.3.1 and 3.5.3.2.2.a"
    ::= { phaseEntry 2 }

--5.2.2.3   Phase Pedestrian Clear Parameter
phasePedestrianClear OBJECT-TYPE
    SYNTAX Integer32 (0..255)
    UNITS "second"
    MAX-ACCESS read-write
    STATUS current
    DESCRIPTION "<Definition> Phase Pedestrian Clear Parameter in seconds.
        This shall control the duration of the Pedestrian Clearance output
        (if present) and the flashing period of the Don't Walk output.
        This parameter shall be used regardless whether the pedestrian
        indication associated with this phase is for a ped-only phase or for
        a pedestrian indication that runs parallel to a vehicle phase.
    <Object Identifier> 1.3.6.1.4.1.1206.4.2.1.1.2.1.3
    <Object Type> P"
    REFERENCE "NEMA TS 2 Clause 3.5.3.1 and 3.5.3.2.2.b"
    ::= { phaseEntry 3 }

--5.2.2.4   Phase Minimum Green Parameter
phaseMinimumGreen OBJECT-TYPE
    SYNTAX Integer32 (0..255)
    UNITS "second"
    MAX-ACCESS read-write
    STATUS current
    DESCRIPTION "<Definition> Phase Minimum Green Parameter in seconds (NEMA
        TS 2 range: 1-255 sec). The first timed portion of the Green interval
        which may be set in consideration of the storage of vehicles between
        the zone of detection for the approach vehicle detector(s) and the
        stop line.
    <Object Identifier> 1.3.6.1.4.1.1206.4.2.1.1.2.1.4
    <Object Type> P"
    REFERENCE "NEMA TS 2 Clause 3.5.3.1 and 3.5.3.2.1.a.(1)"
    ::= { phaseEntry 4 }

--5.2.2.5   Phase Passage Parameter
phasePassage OBJECT-TYPE
    SYNTAX Integer32 (0..255)
    UNITS "decisecond"
    MAX-ACCESS read-write
    STATUS current
    DESCRIPTION "<Definition> Phase Passage Parameter in tenth seconds (0-25.5
        sec). Passage Time, Vehicle Interval, Preset Gap, Vehicle Extension:
        the extensible portion of the Green shall be a function of vehicle
        actuations that occur during the Green interval. The phase shall
        remain in the extensible portion of the Green interval as long as the
        passage timer is not timed out. The timing of this portion of the
        green interval shall be reset with each subsequent vehicle actuation
        and shall not commence to time again until the vehicle actuation is
        removed or the maximum green timer has expired.
    <Object Identifier> 1.3.6.1.4.1.1206.4.2.1.1.2.1.5
    <Object Type> P"
    REFERENCE "NEMA TS 2 Clause 3.5.3.1 and 3.5.3.2.1.a.(2)"
    ::= { phaseEntry 5 }

--5.2.2.6   Phase Maximum Green 1 Parameter
phaseMaximum1 OBJECT-TYPE
    SYNTAX Integer32 (0..999)
    UNITS "second"
    MAX-ACCESS read-write
    STATUS current
    DESCRIPTION "<Definition> Phase Maximum 1 Parameter in seconds (NEMA TS 2
        range: 1-255 sec). This time setting shall determine the maximum
        length of time this phase may be held in Green in the presence of a
        serviceable conflicting call. In the absence of a serviceable
        conflicting call the Maximum Green timer shall be held reset unless
        Max Vehicle Recall is enabled for this phase. This is the default
        maximum value to use. It may be overridden via an external input,
        coordMaximumMode, or other method.
    <Object Identifier> 1.3.6.1.4.1.1206.4.2.1.1.2.1.6
    <Object Type> P"
    REFERENCE "NEMA TS 2 Clause 3.5.3.1, 3.5.3.2.1.a.(3) and 3.5.3.5"
    ::= { phaseEntry 6 }

--5.2.2.7   Phase Maximum Green 2 Parameter
phaseMaximum2 OBJECT-TYPE
    SYNTAX Integer32 (0..999)
    UNITS "second"
    MAX-ACCESS read-write
    STATUS current
    DESCRIPTION "<Definition> Phase Maximum 2 Parameter in seconds (NEMA TS 2
        range: 1-255 sec). This time setting shall determine the maximum
        length of time this phase may be held in Green in the presence of a
        serviceable conflicting call. In the absence of a serviceable
        conflicting call the Maximum Green timer shall be held reset unless
        Max Vehicle Recall is enabled for this phase. This may be implemented
        as the max green timer via an external input, coordMaximumMode or
        other method.
    <Object Identifier> 1.3.6.1.4.1.1206.4.2.1.1.2.1.7
    <Object Type> P"
    REFERENCE "NEMA TS 2 Clause 3.5.3.1, 3.5.3.2.1.a.(3), 3.5.3.5 
     and 3.5.4.1 (7)"
    ::= { phaseEntry 7 }

--5.2.2.8   Phase Yellow Change Parameter
phaseYellowChange OBJECT-TYPE
    SYNTAX Integer32 (0..255)
    UNITS "decisecond"
    MAX-ACCESS read-write
    STATUS current
    DESCRIPTION "<Definition> Phase Yellow Change Parameter in tenth seconds
        (NEMA TS 2 range: 3-25.5 sec). Following the Green interval of each
        phase the CU shall provide a Yellow Change interval which is timed
        according to the Yellow Change parameter for that phase.
    <Object Identifier> 1.3.6.1.4.1.1206.4.2.1.1.2.1.8
    <Object Type> P"
    REFERENCE "NEMA TS 2 Clause 3.5.3.1 and 3.5.3.2.5.a"
    ::= { phaseEntry 8 }

--5.2.2.9   Phase Red Clearance Parameter
phaseRedClear OBJECT-TYPE
    SYNTAX Integer32 (0..255)
    UNITS "decisecond"
    MAX-ACCESS read-write
    STATUS current
    DESCRIPTION "<Definition> Phase Red Clearance Parameter in tenth seconds
        (0-25.5 sec). Following the Yellow Change interval for each phase, the
        CU shall provide a Red Clearance interval which is timed according to
        the Red Clearance parameter for that phase.
    <Object Identifier> 1.3.6.1.4.1.1206.4.2.1.1.2.1.9
    <Object Type> P"
    REFERENCE "NEMA TS 2 Clause 3.5.3.1 and 3.5.3.2.5.b"
    ::= { phaseEntry 9 }

--5.2.2.10  Phase Red Revert Parameter
phaseRedRevert OBJECT-TYPE
    SYNTAX Integer32 (0..255)
    UNITS "decisecond"
    MAX-ACCESS read-write
    STATUS current
    DESCRIPTION "<Definition> Red revert time parameter in tenths of seconds
        (0-25.5 sec). A minimum RED indication to be timed following the
        Yellow Change interval and prior to the next display of Green on the
        same signal output driver group.

        The unitRedRevert parameter shall act as a minimum red revert time for
        all signal displays. The phaseRedRevert parameter may increase the red
        revert time for a specific phase. If the phaseRedRevert parameter is
        less than the unitRedRevert the unitRedRevert time shall be used.
    <Object Identifier> 1.3.6.1.4.1.1206.4.2.1.1.2.1.10
    <Object Type> P"
    ::= { phaseEntry 10 }

--5.2.2.11  Phase Added Initial Parameter
phaseAddedInitial OBJECT-TYPE
    SYNTAX Integer32 (0..255)
    UNITS "decisecond"
    MAX-ACCESS read-write
    STATUS current
    DESCRIPTION "<Definition> Phase Added Initial Parameter in tenths of
        seconds (0-25.5 sec). Added Initial parameter (Seconds / Actuation)
        shall determine the time by which the variable initial time period
        will be increased from zero with each vehicle actuation received
        during the associated phase Yellow and Red intervals.
    <Object Identifier> 1.3.6.1.4.1.1206.4.2.1.1.2.1.11
    <Object Type> P"
    REFERENCE "NEMA TS 2 Clause 3.5.3.1 and 3.5.3.2.1.b.(1).(b)"
    ::= { phaseEntry 11 }

--5.2.2.12  Phase Maximum Initial Parameter
phaseMaximumInitial OBJECT-TYPE
    SYNTAX Integer32 (0..255)
    UNITS "second"
    MAX-ACCESS read-write
    STATUS current
    DESCRIPTION "<Definition> Phase Maximum Initial Parameter in seconds
        (0-255 sec). The maximum value of the variable initial timing period.
        Variable Initial timing shall equal the lesser of [added initial
        (seconds / actuation) * number of actuations] or [ Max Initial ].
        The variable initial time shall not be less than Minimum Green.
    <Object Identifier> 1.3.6.1.4.1.1206.4.2.1.1.2.1.12
    <Object Type> P"
    REFERENCE "NEMA TS 2 Clause 3.5.3.2.1.b.(1).(c)"
    ::= { phaseEntry 12 }

--5.2.2.13  Phase Time Before Reduction Parameter
phaseTimeBeforeReduction OBJECT-TYPE
    SYNTAX Integer32 (0..255)
    UNITS "second"
    MAX-ACCESS read-write
    STATUS current
    DESCRIPTION "<Definition> Phase Time Before Reduction (TBR) Parameter in
        seconds (0-255 sec). The Time Before Reduction period shall begin
        when the phase is Green and there is a serviceable conflicting call.
        If the serviceable conflicting call is removed before completion of
        this time (or time to reduce), the timer shall reset. Upon completion
        of the TBR period or the Cars Before Reduction (CBR) parameter is
        satisfied, whichever occurs first, the linear reduction of the
        allowable gap from the Passage Time shall begin.
    <Object Identifier> 1.3.6.1.4.1.1206.4.2.1.1.2.1.13
    <Object Type> P"
    REFERENCE "NEMA TS 2 Clause 3.5.3.1 and 3.5.3.2.1.b.(2)"
    ::= { phaseEntry 13 }

--5.2.2.14  Phase Cars Before Reduction Parameter
phaseCarsBeforeReduction OBJECT-TYPE
    SYNTAX Integer32 (0..255)
    UNITS "vehicle"
    MAX-ACCESS read-write
    STATUS current
    DESCRIPTION "<Definition> Phase Cars Before Reduction (CBR) Parameter
        (0-255 vehicles). When the phase is Green and the sum of the cars
        waiting (vehicle actuations during Yellow & Red intervals) on
        serviceable conflicting phases equals or exceeds the CBR parameter or
        the Time Before Reduction (TBR) parameter is satisfied, whichever
        occurs first, the linear reduction of the allowable gap from the
        Passage Time shall begin.
    <Object Identifier> 1.3.6.1.4.1.1206.4.2.1.1.2.1.14
    <Object Type> P"
    ::= { phaseEntry 14 }

--5.2.2.15  Phase Time To Reduce Parameter
phaseTimeToReduce OBJECT-TYPE
    SYNTAX Integer32 (0..255)
    UNITS "second"
    MAX-ACCESS read-write
    STATUS current
    DESCRIPTION "<Definition> Phase Time To Reduce Parameter in seconds
        (0-255 sec). This parameter shall control the rate of reduction of the
        allowable gap between the Passage Time and Minimum Gap setting.
    <Object Identifier> 1.3.6.1.4.1.1206.4.2.1.1.2.1.15
    <Object Type> P"
    REFERENCE "NEMA TS 2 Clause 3.5.3.1 and 3.5.3.2.1.b.(2)"
    ::= { phaseEntry 15 }
 
--5.2.2.16  Phase Reduce By Parameter
phaseReduceBy OBJECT-TYPE
    SYNTAX Integer32 (0..255)
    UNITS "decisecond"
    MAX-ACCESS read-write
    STATUS current
    DESCRIPTION "<Definition> This object may be used for volume density gap
        reduction as an alternate to the linear reduction defined by NEMA TS 1
        and TS 2. It contains the tenths of seconds to reduce the gap by
        (0.0 - 25.5 seconds). The frequency of reduction shall produce the
        Minimum Gap after a time equal to the 'phaseTimeToReduce' object.
    <Object Identifier> 1.3.6.1.4.1.1206.4.2.1.1.2.1.16
    <Object Type> P"
    ::= { phaseEntry 16 }

--5.2.2.17  Phase Minimum Gap Parameter
phaseMinimumGap OBJECT-TYPE
    SYNTAX Integer32 (0..255)
    UNITS "decisecond"
    MAX-ACCESS read-write
    STATUS current
    DESCRIPTION "<Definition> Phase Minimum Gap Parameter in tenth seconds
        (0-25.5 sec). The reduction of the allowable gap shall continue until
        the gap reaches a value equal to or less than the minimum gap as set
        on the Minimum Gap control after which the allowable gap shall remain
        fixed at the values set on the Minimum Gap control.
    <Object Identifier> 1.3.6.1.4.1.1206.4.2.1.1.2.1.17
    <Object Type> P"
    REFERENCE "NEMA TS 2 Clause 3.5.3.1 and 3.5.3.2.1.b.(2)"
    ::= { phaseEntry 17 }

--5.2.2.18  Phase Dynamic Max Limit Parameter
phaseDynamicMaxLimit OBJECT-TYPE
    SYNTAX Integer32 (0..255)
    UNITS "second"
    MAX-ACCESS read-write
    STATUS current
    DESCRIPTION "<Definition> This object shall determine either the upper or
        lower limit of the running max in seconds (0-255 sec) during dynamic
        max operation. The normal maximum (i.e. Max1, Max2, etc.) shall
        determine the other limit as follows:
        When this value is larger than the normal maximum, it is the upper limit.
        When this value is smaller than the normal maximum, it is the lower limit.
        Setting dynamicMaxLimit greater than zero enables dynamic max
            operation with the normal maximum used as the initial maximum
            setting. See dynamicMaxStep for details on dynamic max operation.

        Max Vehicle Recall or a failed detector that is assigned to the associated phase shall disable dynamic max operation for the phase.
    <Object Identifier> 1.3.6.1.4.1.1206.4.2.1.1.2.1.18
    <Object Type> P"
    ::= { phaseEntry 18 }

--5.2.2.19  Phase Dynamic Max Step Parameter
phaseDynamicMaxStep OBJECT-TYPE
    SYNTAX Integer32 (0..255)
    UNITS "decisecond"
    MAX-ACCESS read-write
    STATUS current
    DESCRIPTION "<Definition> This object shall determine the automatic adjustment
        to the running max in tenths of seconds (0-25.5). When an ASC decides
        to adjust the running max for the phase, the value of this object shall
        be added or subtracted to the running max per cycle.
    <Object Identifier> 1.3.6.1.4.1.1206.4.2.1.1.2.1.19
    <Object Type> P"
    ::= { phaseEntry 19 }

--5.2.2.20  Phase Startup Parameter
phaseStartup OBJECT-TYPE
    SYNTAX INTEGER { other (1),
                     phaseNotOn (2),
                     greenWalk (3),
                     greenNoWalk (4),
                     yellowChange (5),
                     redClear (6)}
    MAX-ACCESS read-write
    STATUS current
    DESCRIPTION "<Definition> The Phase Startup parameter is an enumerated
        integer which selects the startup state for each phase after
        restoration of a defined power interruption or activation of the
        external start input. The following entries are defined:
            other: this phase is not enabled (phaseOptions bit 0=0 or
                phaseRing=0) or initializes in a state not defined by
                this standard.
            phaseNotOn: this phase initializes in a Red state (the phase is
                not active and no intervals are timing).
            greenWalk: this phase initializes at the beginning of the minimum
                green and walk timing intervals. 
            greenNoWalk: this phase initializes at the beginning of the
                minimum green timing interval.
            yellowChange: this phase initializes at the beginning of the
                Yellow Change interval.
            redClear: this phase initializes at the beginning of the Red
                Clearance interval.
        
        The value for this phase is the same for all phase sets. There is no object in the phaseSetTable corresponding to phaseStartup.
        <Object Identifier> 1.3.6.1.4.1.1206.4.2.1.1.2.1.20
        <Object Type> P2"
    REFERENCE "NEMA TS 2 Clause 3.5.5.1 and 3.5.5.12"
    ::= { phaseEntry 20 }

--5.2.2.21  Phase Options
phaseOptions OBJECT-TYPE
    SYNTAX Integer32 (0..65535)
    MAX-ACCESS read-write
    STATUS current
    DESCRIPTION "<Definition>Optional phase functions
        (0 = False/Disabled, 1 = True/Enabled)
    Bit 15: AddedInitialCalculation - If set (1) the CU shall compare counts
        from all associated AddedInitial detectors and use the largest count
        value for the calculations. If clear (0) the CU shall sum all
        associated AddedInitial detector counts and use this sum for the
        calculations. Support is optional.
    Bit 14: Conditional Service Enable - in multi-ring configurations when set
        to 1 causes a gapped/maxed phase to conditionally service a preceding
        actuated vehicle phase when sufficient time remains before max time out
        of the phase(s) not prepared to terminate. Support is optional.
        REFERENCE  NEMA TS 2 Clause 3.5.3.9
    Bit 13: Actuated Rest-in-Walk - when set to 1 causes an actuated phase to
        rest in Walk when there is no serviceable conflicting call at the end
        of Walk Timing or if Max Vehicle Recall is enabled.
    Bit 12: Guaranteed Passage - when set to 1 enables an actuated phase
        operating in volume density mode (using gap reduction) to retain the
        right of way for the unexpired portion of the Passage time following
        the decision to terminate the green due to a reduced gap. Support is
        optional. The value for this phase is the same for all phase sets.
    Bit 11: Simultaneous Gap Disable - in multi-ring configurations when set
        to 1 disables a gapped out phase from reverting to the extensible
        portion. Support is optional.
        REFERENCE NEMA TS 2 Clause 3.5.5.3
    Bit 10: Dual Entry Phase - in multi-ring configurations when set to 1
        causes the phase to become active upon entry into a concurrency group
        (crossing a barrier) when no calls exist in its ring within its
        concurrency group.
        REFERENCE NEMA TS 2 Clause 3.5.5.3
    Bit 9: Soft Vehicle Recall - when set to 1 causes a call on a phase when
        all conflicting phases are in green dwell or red dwell and there are
        no serviceable conflicting calls. Support is optional.
    Bit 8: Ped. Recall - when set to 1 causes a recurring pedestrian demand
        which shall function in the same manner as an external pedestrian call
        except that it shall not recycle the pedestrian service until a
        conflicting phase is serviced.
        REFERENCE NEMA TS 2 Clause 3.5.3.7
    Bit 7: Max Vehicle Recall - when set to 1 causes a call on a phase such
        that the timing of the Green interval for that phase shall be extended
        to Maximum Green time.
        REFERENCE NEMA TS 2 Clause 3.5.3.5
    Bit 6: Min. Vehicle Recall - when set to 1 causes recurring demand for
        vehicle service on the phase when that phase is not in its Green
        interval.
        REFERENCE NEMA TS 2 Clause 3.5.3.6
    Bit 5: Non Lock Detector Memory - when set to 0 will cause the call to be
        locked at the beginning of the yellow interval. When set to 1 call
        locking will depend on the detectorOptions object.
        REFERENCE NEMA TS 2 Clause 3.5.3.4
    Bit 4: Non-Actuated 2 - when set to 1 causes a phase to respond to the
        Call To Non-Actuated 2 input (if present) or other method. Support
        is optional.
        REFERENCE NEMA TS 2 Clause 3.5.5.5.8
    Bit 3: Non-Actuated 1 - when set to 1 causes a phase to respond to the
        Call To Non-Actuated 1 input (if present) or other method. Support is
        optional.
        REFERENCE NEMA TS 2 Clause 3.5.5.5.8
    Bit 2: Automatic Flash Exit Phase - The CU shall move immediately to the
        beginning of the phase(s) programmed as Exit Phase(s) when Automatic
        Flash terminates. The value for this phase is the same for all phase sets. Support is optional.
        REFERENCE NEMA TS 2 Clause 3.9.1.2.1
    Bit 1: Automatic Flash Entry Phase - When Automatic Flash is called, the
        CU shall service the Entry Phase(s), clear to an All Red, then
        initiate flashing operation. The value for this phase is the same for all phase sets. Support is optional.
        REFERENCE NEMA TS 2 Clause 3.9.1.2.1
    Bit 0: Enabled Phase - provide a means to define whether this phase is
        used in the current configuration. A disabled phase shall not provide
        any outputs nor respond to any phase inputs. The object phaseRing = 0
        has the same effect. The value for this phase is the same for all phase sets.
    <Object Identifier> 1.3.6.1.4.1.1206.4.2.1.1.2.1.22
    <Object Type> P2"
    ::= { phaseEntry 21 }

--5.2.2.22  Phase Ring
phaseRing OBJECT-TYPE
    SYNTAX Integer32 (0..255)
    UNITS "ring"
    MAX-ACCESS read-write
    STATUS current
    DESCRIPTION "<Definition> Phase ring number (1..maxRings) that identified
        the ring which contains the associated phase. This value must not
        exceed the maxRings object value. If the ring number is zero, the
        phase is disabled (phaseOptions Bit 0 = 0 has the same effect).

    The value for this phase is the same for all phase sets. There is no object in the phaseSetTable corresponding to phaseRing.

    <Object Identifier> 1.3.6.1.4.1.1206.4.2.1.1.2.1.22
    <Object Type> P2"
    ::= { phaseEntry 22 }

--5.2.2.23  Phase Concurrency
phaseConcurrency OBJECT-TYPE
    SYNTAX OCTET STRING
    MAX-ACCESS read-write
    STATUS current
    DESCRIPTION "<Definition>Each octet contains a phase number (binary value)
        that may run concurrently with the associated phase. Phases that are
        contained in the same ring may NOT run concurrently.

        The value for this phase is the same for all phase sets. There is no object in the phaseSetTable corresponding to phaseConcurrency.
    
    <Object Identifier> 1.3.6.1.4.1.1206.4.2.1.1.2.1.23
    <Object Type> P2"
    ::= { phaseEntry 23 }

--5.2.2.24  Phase Maximum Green 3 Parameter
phaseMaximum3 OBJECT-TYPE
    SYNTAX Integer32 (0..999)
    UNITS "second"
    MAX-ACCESS read-write
    STATUS current
    DESCRIPTION "<Definition> Phase Maximum 3 Parameter in seconds. This time
        setting shall determine the maximum length of time this phase may be
        held in Green in the presence of a serviceable conflicting call. In
        the absence of a serviceable conflicting call, the Maximum Green timer
        shall be held reset unless Max Vehicle Recall is enabled for this
        phase. This may be implemented as the max green timer via an external
        input, coordMaximumMode or other method.
    <Object Identifier> 1.3.6.1.4.1.1206.4.2.1.1.2.1.24
    <Object Type> P"
    ::= { phaseEntry 24 }

--5.2.2.25  Phase Ped Clearance During Vehicle Clearance Parameter
phasePedClearDuringVehicleClear OBJECT-TYPE
    SYNTAX Integer32 (0..255)
    UNITS "decisecond"
    MAX-ACCESS read-write
    STATUS current
    DESCRIPTION "<Definition> The amount of time that the pedestrian clearance
        may extend into the vehicle clearance time (yellow and red) for a
        phase. This parameter is expressed in 0.1 second increments ranging
        from 0.0 to 25.5 seconds.

        This object was named phaseYellowandRedChangeTimeBeforeEndPedClear in 1202 v03.
    <Object Identifier> 1.3.6.1.4.1.1206.4.2.1.1.2.1.25
    <Object Type> P"
    ::= { phaseEntry 25 }

--5.2.2.26  Phase Pedestrian Service Limit Parameter
phasePedServiceLimit OBJECT-TYPE
    SYNTAX Integer32 (0..255)
    MAX-ACCESS read-write
    STATUS current
    DESCRIPTION "<Definition> This parameter indicates whether and how many
        times this phase is allowed to recycle the pedestrian movement during
        a cycle. This parameter is typically used for ped-only, signalized intersections
        (mostly mid-block) that are within a coordinated roadway. If set to
        '1', no recycle is allowed and the pedestrian movement can be shown
        only up to once. If set to '2', the pedestrian movement can be shown
        up to twice during a cycle, etc. A value of zero means there is no limit. 

        This object was named phasePedWalkService in 1202 v03.

    <Object Identifier> 1.3.6.1.4.1.1206.4.2.1.1.2.1.26
    <Object Type> P"
    DEFVAL { 0 }
    ::= { phaseEntry 26 }

--5.2.2.27  Phase Don't Walk Revert Parameter
phaseDontWalkRevert OBJECT-TYPE
    SYNTAX Integer32 (0..255)
    UNITS "decisecond"
    MAX-ACCESS read-write
    STATUS current
    DESCRIPTION "<Definition> Don't Walk revert time parameter in tenth
        seconds. A minimum DON'T WALK indication to be timed following the
        pedestrian clearance interval prior to the next WALK indication on
        the same signal output driver group.
    <Object Identifier> 1.3.6.1.4.1.1206.4.2.1.1.2.1.27
    <Object Type> P"
    ::= { phaseEntry 27 }

--5.2.2.28  Phase Alternate Pedestrian Clearance Time Parameter
phasePedAlternateClearance OBJECT-TYPE
    SYNTAX Integer32 (0..255)
    UNITS "second"
    MAX-ACCESS read-write
    STATUS current
    DESCRIPTION "<Definition> An alternate (replacement) time, in seconds,
        for the duration of the pedestrian clearance output (if present) and
        the flashing DON'T WALK indication. 

        This parameter may be used for a parallel pedestrian indication in
        conjunction with a vehicle phase or with a ped-only phase to support extend pedestrian clearance times. 
    <Object Identifier> 1.3.6.1.4.1.1206.4.2.1.1.2.1.28
    <Object Type> P"
    ::= { phaseEntry 28 }

--5.2.2.29  Phase Alternate Pedestrian Walk Time Parameter
phasePedAlternateWalk OBJECT-TYPE
    SYNTAX Integer32 (0..255)
    UNITS "second"
    MAX-ACCESS read-write
    STATUS current
    DESCRIPTION "<Definition> An alternate (replacement) time, in seconds, for
        a pedestrian Walk. This shall control the amount of time the WALK
        indication shall be displayed.

        This parameter may be used for a parallel pedestrian indication in
        conjunction with a vehicle phase or with a ped-only phase to support extended walk times.
    <Object Identifier> 1.3.6.1.4.1.1206.4.2.1.1.2.1.29
    <Object Type> P"
    ::= { phaseEntry 29 }

--5.2.2.30  Phase Pedestrian Advance Walk Time Parameter
phasePedAdvanceWalkTime OBJECT-TYPE
    SYNTAX Integer32 (0..255)
    UNITS "decisecond"
    MAX-ACCESS read-write
    STATUS current
    DESCRIPTION "<Definition> The amount of time, in tenths of a second from
        0 to 25.5 seconds, that the phase's pedestrian WALK
        indication starts before the start of the phase's vehicle GREEN indication.
        
        This parameter is used in response to a pedestrian detector input as configured in pedestrianDetectorOptions or if pedestrian recall is enabled.
    <Object Identifier> 1.3.6.1.4.1.1206.4.2.1.1.2.1.30
    <Object Type> P"
    DEFVAL { 0 }
    ::= { phaseEntry 30 }

--5.2.2.31  Phase Pedestrian Delay Walk Time Parameter
phasePedDelayTime OBJECT-TYPE
    SYNTAX Integer32 (0..255)
    UNITS "decisecond"
    MAX-ACCESS read-write
    STATUS current
    DESCRIPTION "<Definition> The amount of time, in tenths of a second from
        0 to 25.5 seconds, that the phase's pedestrian WALK
        indication starts after the start of the phase's vehicle GREEN indication. 
        
    This parameter is used in response to a pedestrian detector input.

    <Object Identifier> 1.3.6.1.4.1.1206.4.2.1.1.2.1.31
    <Object Type> P"
    DEFVAL { 0 }
    ::= { phaseEntry 31 }

--5.2.2.32  Phase Advance Green Indication Start Time Parameter
phaseAdvWarnGrnStartTime OBJECT-TYPE
    SYNTAX Integer32 (0..255)
    UNITS "decisecond"
    MAX-ACCESS read-write
    STATUS current
    DESCRIPTION "<Definition> The amount of time, in tenths of a second for a
        period of 0.0 to 25.5 seconds, that an advance warning signal
        indication is displayed before the start of phase Green. The warning
        signal is placed upstream of the phase's approach and indicates that
        the phase's GREEN indication is about to start or has started.

        The duration of the advance green indication should not exceed the total amount of vehicle clearance time of the phase(s) that is being terminated prior to the start of this phase.

        Note: The Advance Warning Green terminates at the end of the green.
    <Object Identifier> 1.3.6.1.4.1.1206.4.2.1.1.2.1.32
    <Object Type> P"
    ::= { phaseEntry 32 }

--5.2.2.33  Phase Advance Red Indication Start Time Parameter
phaseAdvWarnRedStartTime OBJECT-TYPE
    SYNTAX Integer32 (0..255)
    UNITS "decisecond"
    MAX-ACCESS read-write
    STATUS current
    DESCRIPTION "<Definition> The amount of time, in tenths of a second for a
        range of 0.0 to 25.5 seconds, prior to the start of the phase's RED
        indication that an advance warning signal, placed upstream of the
        phase's approach, turns on.
        Note: The Advance Warning Red terminates at the end of Red.
    <Object Identifier> 1.3.6.1.4.1.1206.4.2.1.1.2.1.33
    <Object Type> P"
    ::= { phaseEntry 33 }

--5.2.2.34  Phase Alternate Minimum Green Time During Transitions
phaseAltMinTimeTransition OBJECT-TYPE
    SYNTAX Integer32 (0..255)
    UNITS "second"
    MAX-ACCESS read-write
    STATUS current
    DESCRIPTION "<Definition> This object indicates the alternate minimum
        green time that is used during transitions, in seconds from 1 to 255
        seconds. This object can be applied during transitions or signal
        priority. A value of zero indicates that this object is not used during
        transitions. This value shall not exceed phaseMinimumGreen for this phase. 
    <Object Identifier> 1.3.6.1.4.1.1206.4.2.1.1.2.1.34
    <Object Type> P"
    DEFVAL { 0 }
    ::= { phaseEntry 34 }

--5.2.2.35  Phase Alternate Walk Time During Transitions
phaseWalkDuringTransition OBJECT-TYPE
    SYNTAX Integer32 (0..255)
    UNITS "second"
    MAX-ACCESS read-write
    STATUS current
    DESCRIPTION "<Definition> This object indicates the alternate walk time that is used during transitions, in seconds from 1 to 255
        seconds. This object can be applied during transitions or signal priority. A value of zero indicates that this object is not used during
        transitions. This value shall not exceed phaseWalk for this phase. 
    <Object Identifier> 1.3.6.1.4.1.1206.4.2.1.1.2.1.35
    <Object Type> P"
    DEFVAL { 0 }
    ::= { phaseEntry 35 }

--5.2.2.36  Phase Alternate Pedestrian Clearance Time During Transitions
phasePedClearDuringTransition OBJECT-TYPE
    SYNTAX Integer32 (0..255)
    UNITS "second"
    MAX-ACCESS read-write
    STATUS current
    DESCRIPTION "<Definition> This object indicates the alternate minimum pedestrian clearance time walk time that is used during transitions, in seconds from 1 to 255 seconds. This object can be applied during transitions or signal priority. A value of zero indicates that this object is not used during transitions. This value shall not exceed phasePedestrianClear for this phase.
    <Object Identifier> 1.3.6.1.4.1.1206.4.2.1.1.2.1.36
    <Object Type> P"
    DEFVAL { 0 }
    ::= { phaseEntry 36 }

--5.2.3 Maximum Phase Groups
    maxPhaseGroups OBJECT-TYPE
    SYNTAX Integer32 (1..32)
    UNITS   "groups"
    MAX-ACCESS read-only
    STATUS current
    DESCRIPTION "<Definition> The Maximum Number of Phase Groups (8 Phases per group) this Controller Unit supports. This value is equal to TRUNCATE [(maxPhases + 7) / 8].
    This object indicates the maximum rows which shall appear in the phaseStatusGroupTable and phaseControlGroupTable.
    <Object Identifier> 1.3.6.1.4.1.1206.4.2.1.1.3
    <Object Type> S"
    ::= { phase 3 }

--5.2.4 Phase Status Group Table
phaseStatusGroupTable OBJECT-TYPE
    SYNTAX SEQUENCE OF PhaseStatusGroupEntry
    MAX-ACCESS not-accessible
    STATUS current
    DESCRIPTION "<Definition> A table containing Controller Unit Phase Output
        (Red, Yellow, & Green) and Call (vehicle & pedestrian) status in
        groups of eight Phases. The number of rows in this table is equal to
        the maxPhaseGroups object.
    <TableType> static
    <Object Identifier> 1.3.6.1.4.1.1206.4.2.1.1.4"
    ::= { phase 4 }

phaseStatusGroupEntry OBJECT-TYPE
    SYNTAX PhaseStatusGroupEntry
    MAX-ACCESS not-accessible
    STATUS current
    DESCRIPTION "<Definition> Red, Yellow, & Green Output Status and Vehicle
        and Pedestrian Call for eight Controller Unit Phases. 
    <Object Identifier> 1.3.6.1.4.1.1206.4.2.1.1.4.1"
    INDEX   { phaseStatusGroupNumber }
    ::= { phaseStatusGroupTable 1 }

 
PhaseStatusGroupEntry ::= SEQUENCE { 
    phaseStatusGroupNumber      Integer32,
    phaseStatusGroupReds        Integer32,
    phaseStatusGroupYellows     Integer32,
    phaseStatusGroupGreens      Integer32,
    phaseStatusGroupDontWalks   Integer32,
    phaseStatusGroupPedClears   Integer32,
    phaseStatusGroupWalks       Integer32,
    phaseStatusGroupVehCalls    Integer32,
    phaseStatusGroupPedCalls    Integer32,
    phaseStatusGroupPhaseOns    Integer32,
    phaseStatusGroupPhaseNexts  Integer32 }

--5.2.4.1   Phase Status Group Number
phaseStatusGroupNumber OBJECT-TYPE
    SYNTAX Integer32 (1..32)
    UNITS   "group"
    MAX-ACCESS not-accessible
    STATUS current
    DESCRIPTION "<Definition> The Phase Status Group number for objects in
        this row. This value shall not exceed the maxPhaseGroups object value.
    <Object Identifier> 1.3.6.1.4.1.1206.4.2.1.1.4.1.1"
    ::= { phaseStatusGroupEntry 1 }

--5.2.4.2   Phase Status Group Reds
phaseStatusGroupReds OBJECT-TYPE
    SYNTAX Integer32 (0..255)
    MAX-ACCESS read-only
    STATUS current
    DESCRIPTION "<Definition> Phase Red Output Status Mask, when a bit = 1,
        the Phase Red is currently active. When a bit = 0, the Phase Red is
        NOT currently active. This does not include phases that are disabled. 
            Bit 7: Phase # = (phaseStatusGroupNumber * 8)
            Bit 6: Phase # = (phaseStatusGroupNumber * 8) - 1
            Bit 5: Phase # = (phaseStatusGroupNumber * 8) - 2
            Bit 4: Phase # = (phaseStatusGroupNumber * 8) - 3
            Bit 3: Phase # = (phaseStatusGroupNumber * 8) - 4
            Bit 2: Phase # = (phaseStatusGroupNumber * 8) - 5
            Bit 1: Phase # = (phaseStatusGroupNumber * 8) - 6
            Bit 0: Phase # = (phaseStatusGroupNumber * 8) - 7
    <Object Identifier> 1.3.6.1.4.1.1206.4.2.1.1.4.1.2
    <Object Type> S"
    ::= { phaseStatusGroupEntry 2 }

--5.2.4.3   Phase Status Group Yellows
phaseStatusGroupYellows OBJECT-TYPE
    SYNTAX Integer32 (0..255)
    MAX-ACCESS read-only
    STATUS current
    DESCRIPTION "<Definition> Phase Yellow Output Status Mask, when a bit = 1,
        the Phase Yellow is currently active. When a bit = 0, the Phase
        Yellow is NOT currently active.
            Bit 7: Phase # = (phaseStatusGroupNumber * 8)
            Bit 6: Phase # = (phaseStatusGroupNumber * 8) - 1
            Bit 5: Phase # = (phaseStatusGroupNumber * 8) - 2
            Bit 4: Phase # = (phaseStatusGroupNumber * 8) - 3
            Bit 3: Phase # = (phaseStatusGroupNumber * 8) - 4
            Bit 2: Phase # = (phaseStatusGroupNumber * 8) - 5
            Bit 1: Phase # = (phaseStatusGroupNumber * 8) - 6
            Bit 0: Phase # = (phaseStatusGroupNumber * 8) - 7
    <Object Identifier> 1.3.6.1.4.1.1206.4.2.1.1.4.1.3
    <Object Type> S"
    ::= { phaseStatusGroupEntry 3 }

--5.2.4.4   Phase Status Group Greens
phaseStatusGroupGreens OBJECT-TYPE
    SYNTAX Integer32 (0..255)
    MAX-ACCESS read-only
    STATUS current
    DESCRIPTION "<Definition> Phase Green Output Status Mask, when a bit = 1,
        the Phase Green is currently active. When a bit = 0, the Phase Green
        is NOT currently active.
            Bit 7: Phase # = (phaseStatusGroupNumber * 8)
            Bit 6: Phase # = (phaseStatusGroupNumber * 8) - 1
            Bit 5: Phase # = (phaseStatusGroupNumber * 8) - 2
            Bit 4: Phase # = (phaseStatusGroupNumber * 8) - 3
            Bit 3: Phase # = (phaseStatusGroupNumber * 8) - 4
            Bit 2: Phase # = (phaseStatusGroupNumber * 8) - 5
            Bit 1: Phase # = (phaseStatusGroupNumber * 8) - 6
            Bit 0: Phase # = (phaseStatusGroupNumber * 8) - 7
    <Object Identifier> 1.3.6.1.4.1.1206.4.2.1.1.4.1.4
    <Object Type> S"
    ::= { phaseStatusGroupEntry 4 }
 
--5.2.4.5   Phase Status Group Don't Walks
phaseStatusGroupDontWalks OBJECT-TYPE
    SYNTAX Integer32 (0..255)
    MAX-ACCESS read-only
    STATUS current
    DESCRIPTION "<Definition> Phase Dont Walk Output Status Mask, when a
        bit = 1, the Phase Dont Walk is currently active. When a bit = 0,
        the Phase Dont Walk is NOT currently active.
            Bit 7: Phase # = (phaseStatusGroupNumber * 8)
            Bit 6: Phase # = (phaseStatusGroupNumber * 8) - 1
            Bit 5: Phase # = (phaseStatusGroupNumber * 8) - 2
            Bit 4: Phase # = (phaseStatusGroupNumber * 8) - 3
            Bit 3: Phase # = (phaseStatusGroupNumber * 8) - 4
            Bit 2: Phase # = (phaseStatusGroupNumber * 8) - 5
            Bit 1: Phase # = (phaseStatusGroupNumber * 8) - 6
            Bit 0: Phase # = (phaseStatusGroupNumber * 8) - 7
    <Object Identifier> 1.3.6.1.4.1.1206.4.2.1.1.4.1.5
    <Object Type> S"
    ::= { phaseStatusGroupEntry 5 }

--5.2.4.6   Phase Status Group Pedestrian Clears
phaseStatusGroupPedClears OBJECT-TYPE
    SYNTAX Integer32 (0..255)
    MAX-ACCESS read-only
    STATUS current
    DESCRIPTION "<Definition> Phase Ped Clear Output Status Mask, when a
        bit = 1, the Phase Ped Clear is currently active. When a bit = 0,
        the Phase Ped Clear is NOT currently active.
            Bit 7: Phase # = (phaseStatusGroupNumber * 8)
            Bit 6: Phase # = (phaseStatusGroupNumber * 8) - 1
            Bit 5: Phase # = (phaseStatusGroupNumber * 8) - 2
            Bit 4: Phase # = (phaseStatusGroupNumber * 8) - 3
            Bit 3: Phase # = (phaseStatusGroupNumber * 8) - 4
            Bit 2: Phase # = (phaseStatusGroupNumber * 8) - 5
            Bit 1: Phase # = (phaseStatusGroupNumber * 8) - 6
            Bit 0: Phase # = (phaseStatusGroupNumber * 8) - 7
    <Object Identifier> 1.3.6.1.4.1.1206.4.2.1.1.4.1.6
    <Object Type> S"
    ::= { phaseStatusGroupEntry 6 }
 
--5.2.4.7   Phase Status Group Walks
phaseStatusGroupWalks OBJECT-TYPE
    SYNTAX Integer32 (0..255)
    MAX-ACCESS read-write
    STATUS current
    DESCRIPTION "<Definition> Phase Walk Output Status Mask, when a bit = 1,
        the Phase Walk is currently active. When a bit = 0, the Phase Walk
        is NOT currently active.
            Bit 7: Phase # = (phaseStatusGroupNumber * 8)
            Bit 6: Phase # = (phaseStatusGroupNumber * 8) - 1
            Bit 5: Phase # = (phaseStatusGroupNumber * 8) - 2
            Bit 4: Phase # = (phaseStatusGroupNumber * 8) - 3
            Bit 3: Phase # = (phaseStatusGroupNumber * 8) - 4
            Bit 2: Phase # = (phaseStatusGroupNumber * 8) - 5
            Bit 1: Phase # = (phaseStatusGroupNumber * 8) - 6
            Bit 0: Phase # = (phaseStatusGroupNumber * 8) - 7
    <Object Identifier> 1.3.6.1.4.1.1206.4.2.1.1.4.1.7
    <Object Type> S"
    ::= { phaseStatusGroupEntry 7 }

--5.2.4.8   Phase Status Group Vehicle Calls
phaseStatusGroupVehCalls OBJECT-TYPE
    SYNTAX Integer32 (0..255)
    MAX-ACCESS read-only
    STATUS current
    DESCRIPTION "<Definition> Phase Vehicle Call Status Mask, when a bit = 1,
        the Phase vehicle currently has a call for service, regardless of where the call was placed from. 
        When a bit = 0, the Phase vehicle currently does NOT have a call for service.
            Bit 7: Phase # = (phaseStatusGroupNumber * 8)
            Bit 6: Phase # = (phaseStatusGroupNumber * 8) - 1
            Bit 5: Phase # = (phaseStatusGroupNumber * 8) - 2
            Bit 4: Phase # = (phaseStatusGroupNumber * 8) - 3
            Bit 3: Phase # = (phaseStatusGroupNumber * 8) - 4
            Bit 2: Phase # = (phaseStatusGroupNumber * 8) - 5
            Bit 1: Phase # = (phaseStatusGroupNumber * 8) - 6
            Bit 0: Phase # = (phaseStatusGroupNumber * 8) - 7
    <Object Identifier> 1.3.6.1.4.1.1206.4.2.1.1.4.1.8
    <Object Type> S"
    ::= { phaseStatusGroupEntry 8 }
 
--5.2.4.9   Phase Status Group Pedestrian Calls
phaseStatusGroupPedCalls OBJECT-TYPE
    SYNTAX Integer32 (0..255)
    MAX-ACCESS read-only
    STATUS current
    DESCRIPTION "<Definition> Phase Pedestrian Call Status Mask, when a
        bit = 1, the  Phase pedestrian currently has a call for service, regardless of where the call was placed from.
        When a bit = 0, the Phase pedestrian currently does NOT have a
        call for service.
            Bit 7: Phase # = (phaseStatusGroupNumber * 8)
            Bit 6: Phase # = (phaseStatusGroupNumber * 8) - 1
            Bit 5: Phase # = (phaseStatusGroupNumber * 8) - 2
            Bit 4: Phase # = (phaseStatusGroupNumber * 8) - 3
            Bit 3: Phase # = (phaseStatusGroupNumber * 8) - 4
            Bit 2: Phase # = (phaseStatusGroupNumber * 8) - 5
            Bit 1: Phase # = (phaseStatusGroupNumber * 8) - 6
            Bit 0: Phase # = (phaseStatusGroupNumber * 8) - 7
    <Object Identifier> 1.3.6.1.4.1.1206.4.2.1.1.4.1.9
    <Object Type> S"
    ::= { phaseStatusGroupEntry 9 }

--5.2.4.10  Phase Status Group Phase Ons
phaseStatusGroupPhaseOns OBJECT-TYPE
    SYNTAX Integer32 (0..255)
    MAX-ACCESS read-only
    STATUS current
    DESCRIPTION "<Definition> Phase On Status Mask, when a bit = 1, the Phase
        is currently active. When a bit = 0, the Phase currently is NOT
        active. The phase is ON during the Green, Yellow, & Red Clearance
        intervals of that phase. It shall be permissible for this
        STATUS to be True (bit=1) during the Red Dwell state.
            Bit 7: Phase # = (phaseStatusGroupNumber * 8)
            Bit 6: Phase # = (phaseStatusGroupNumber * 8) - 1
            Bit 5: Phase # = (phaseStatusGroupNumber * 8) - 2
            Bit 4: Phase # = (phaseStatusGroupNumber * 8) - 3
            Bit 3: Phase # = (phaseStatusGroupNumber * 8) - 4
            Bit 2: Phase # = (phaseStatusGroupNumber * 8) - 5
            Bit 1: Phase # = (phaseStatusGroupNumber * 8) - 6
            Bit 0: Phase # = (phaseStatusGroupNumber * 8) - 7
    <Object Identifier> 1.3.6.1.4.1.1206.4.2.1.1.4.1.10
    <Object Type> S"
    ::= { phaseStatusGroupEntry 10 }
 
--5.2.4.11  Phase Status Group Phase Nexts
phaseStatusGroupPhaseNexts OBJECT-TYPE
    SYNTAX Integer32 (0..255)
    MAX-ACCESS read-only
    STATUS current
    DESCRIPTION "<Definition> Phase Next Status Mask, when a bit = 1, the
        Phase currently is committed to be NEXT in sequence & remains present
        until the phase becomes active (On/Timing). When a bit = 0, the Phase
        currently is NOT committed to be NEXT in sequence. The phase next to
        be serviced shall be determined at the end of the green interval of
        the terminating phase; except that if the decision cannot be made at
        the end of the Green interval, it shall not be made until after the
        end of all Vehicle Change & Clearance intervals.
            Bit 7: Phase # = (phaseStatusGroupNumber * 8)
            Bit 6: Phase # = (phaseStatusGroupNumber * 8) - 1
            Bit 5: Phase # = (phaseStatusGroupNumber * 8) - 2
            Bit 4: Phase # = (phaseStatusGroupNumber * 8) - 3
            Bit 3: Phase # = (phaseStatusGroupNumber * 8) - 4
            Bit 2: Phase # = (phaseStatusGroupNumber * 8) - 5
            Bit 1: Phase # = (phaseStatusGroupNumber * 8) - 6
            Bit 0: Phase # = (phaseStatusGroupNumber * 8) - 7
    <Object Identifier> 1.3.6.1.4.1.1206.4.2.1.1.4.1.11
    <Object Type> S"
    ::= { phaseStatusGroupEntry 11 }

--5.2.5 Phase Control Table
phaseControlGroupTable OBJECT-TYPE
    SYNTAX SEQUENCE OF PhaseControlGroupEntry
    UNITS "group"
    MAX-ACCESS not-accessible
    STATUS current
    DESCRIPTION "<Definition> A table containing Controller Unit Phase Control
        in groups of eight phases. The number of rows in this table is equal
        to the maxPhaseGroups object.
    <TableType> static
    <Object Identifier> 1.3.6.1.4.1.1206.4.2.1.1.5"
    ::= { phase 5 }

phaseControlGroupEntry OBJECT-TYPE
    SYNTAX PhaseControlGroupEntry
    MAX-ACCESS not-accessible
    STATUS current
    DESCRIPTION "<Definition> Phase Control for eight Controller Unit phases.
    <Object Identifier> 1.3.6.1.4.1.1206.4.2.1.1.5.1"
    INDEX   { phaseControlGroupNumber }
    ::= { phaseControlGroupTable 1 }

PhaseControlGroupEntry ::= SEQUENCE { 
    phaseControlGroupNumber     Integer32,
    phaseControlGroupPhaseOmit  Integer32,
    phaseControlGroupPedOmit    Integer32,
    phaseControlGroupHold       Integer32,
    phaseControlGroupForceOff   Integer32,
    phaseControlGroupVehCall    Integer32,
    phaseControlGroupPedCall    Integer32 }

--5.2.5.1   Phase Control Group Number
phaseControlGroupNumber OBJECT-TYPE
    SYNTAX Integer32 (1..32)
    UNITS   "group"
    MAX-ACCESS not-accessible
    STATUS current
    DESCRIPTION "<Definition> The Phase Control Group number for objects in
        this row. This value shall not exceed the maxPhaseGroups object value.
    <Object Identifier> 1.3.6.1.4.1.1206.4.2.1.1.5.1.1"
    ::= { phaseControlGroupEntry 1 }

--5.2.5.2   Phase Omit Control
phaseControlGroupPhaseOmit OBJECT-TYPE
    SYNTAX Integer32 (0..255)
    MAX-ACCESS read-write
    STATUS current
    DESCRIPTION "<Definition> This object is used to allow a remote entity to
        omit phases from being serviced in the device. When a bit = 1, the
        device shall activate the System Phase Omit control for that phase.
        When a bit = 0, the device shall not activate the System Phase Omit
        control for that phase.
            Bit 7: Phase # = (phaseControlGroupNumber * 8)
            Bit 6: Phase # = (phaseControlGroupNumber * 8) - 1
            Bit 5: Phase # = (phaseControlGroupNumber * 8) - 2
            Bit 4: Phase # = (phaseControlGroupNumber * 8) - 3
            Bit 3: Phase # = (phaseControlGroupNumber * 8) - 4
            Bit 2: Phase # = (phaseControlGroupNumber * 8) - 5
            Bit 1: Phase # = (phaseControlGroupNumber * 8) - 6
            Bit 0: Phase # = (phaseControlGroupNumber * 8) - 7
        The device shall reset this object to ZERO when in BACKUP Mode. A
        write to this object shall reset the Backup timer to ZERO
        (see unitBackupTime).
    <Object Identifier> 1.3.6.1.4.1.1206.4.2.1.1.5.1.2
    <Object Type> C"
    REFERENCE "NEMA TS 2 Clause 3.5.3.11.2"
    ::= { phaseControlGroupEntry 2 }

--5.2.5.3   Pedestrian Omit Control
phaseControlGroupPedOmit OBJECT-TYPE
    SYNTAX Integer32 (0..255)
    MAX-ACCESS read-write
    STATUS current
    DESCRIPTION "<Definition> This object is used to allow a remote entity to
        omit peds from being serviced in the device. When a bit = 1, the
        device shall activate the System Ped Omit control for that phase. When
        a bit = 0, the device shall not activate the System Ped Omit control
        for that phase.
            Bit 7: Phase # = (phaseControlGroupNumber * 8)
            Bit 6: Phase # = (phaseControlGroupNumber * 8) - 1
            Bit 5: Phase # = (phaseControlGroupNumber * 8) - 2
            Bit 4: Phase # = (phaseControlGroupNumber * 8) - 3
            Bit 3: Phase # = (phaseControlGroupNumber * 8) - 4
            Bit 2: Phase # = (phaseControlGroupNumber * 8) - 5
            Bit 1: Phase # = (phaseControlGroupNumber * 8) - 6
            Bit 0: Phase # = (phaseControlGroupNumber * 8) - 7
        The device shall reset this object to ZERO when in BACKUP Mode. A
        write to this object shall reset the Backup timer to ZERO 
        (see unitBackupTime).
    <Object Identifier> 1.3.6.1.4.1.1206.4.2.1.1.5.1.3
    <Object Type> C"
    REFERENCE "NEMA TS 2 Clause 3.5.3.11.3"
    ::= { phaseControlGroupEntry 3 }

--5.2.5.4   Phase Hold Control
phaseControlGroupHold OBJECT-TYPE
    SYNTAX Integer32 (0..255)
    MAX-ACCESS read-write
    STATUS current
    DESCRIPTION "<Definition> This object is used to allow a remote entity to
        hold phases in the device. When a bit = 1, the device shall activate
        the System Phase Hold control for that phase. When a bit = 0, the
        device shall not activate the System Phase Hold control for that phase.
            Bit 7: Phase # = (phaseControlGroupNumber * 8)
            Bit 6: Phase # = (phaseControlGroupNumber * 8) - 1
            Bit 5: Phase # = (phaseControlGroupNumber * 8) - 2
            Bit 4: Phase # = (phaseControlGroupNumber * 8) - 3
            Bit 3: Phase # = (phaseControlGroupNumber * 8) - 4
            Bit 2: Phase # = (phaseControlGroupNumber * 8) - 5
            Bit 1: Phase # = (phaseControlGroupNumber * 8) - 6
            Bit 0: Phase # = (phaseControlGroupNumber * 8) - 7
        The device shall reset this object to ZERO when in BACKUP Mode. A
        write to this object shall reset the Backup timer to ZERO
        (see unitBackupTime).
    <Object Identifier> 1.3.6.1.4.1.1206.4.2.1.1.5.1.4
    <Object Type> C"
    REFERENCE "NEMA TS 2 Clause 3.5.3.11.1"
    ::= { phaseControlGroupEntry 4 }

--5.2.5.5   Phase Force Off Control
phaseControlGroupForceOff OBJECT-TYPE
    SYNTAX Integer32 (0..255)
    MAX-ACCESS read-write
    STATUS current
    DESCRIPTION "<Definition> This object is used to apply force offs on a per
        phase basis. When a bit = 1, the device shall activate the System
        Phase Force Off control for that phase. When a bit = 0, the device
        shall not activate the System Phase Force Off control for that phase.
        When the phase green terminates, the associated bit shall be reset to zero.
            Bit 7: Phase # = (phaseControlGroupNumber * 8)
            Bit 6: Phase # = (phaseControlGroupNumber * 8) - 1
            Bit 5: Phase # = (phaseControlGroupNumber * 8) - 2
            Bit 4: Phase # = (phaseControlGroupNumber * 8) - 3
            Bit 3: Phase # = (phaseControlGroupNumber * 8) - 4
            Bit 2: Phase # = (phaseControlGroupNumber * 8) - 5
            Bit 1: Phase # = (phaseControlGroupNumber * 8) - 6
            Bit 0: Phase # = (phaseControlGroupNumber * 8) - 7
        The device shall reset this object to ZERO when in BACKUP Mode. A
        write to this object shall reset the Backup timer to ZERO
        (see unitBackupTime).
    <Object Identifier> 1.3.6.1.4.1.1206.4.2.1.1.5.1.5
    <Object Type> C"
    ::= { phaseControlGroupEntry 5 }

--5.2.5.6   Phase Vehicle Call Control
phaseControlGroupVehCall OBJECT-TYPE
    SYNTAX Integer32 (0..255)
    MAX-ACCESS read-write
    STATUS current
    DESCRIPTION "<Definition> This object is used to allow a remote entity to
        place calls for vehicle service in the device. When a bit = 1, the
        device shall place a call for vehicle service on that phase. When a
        bit = 0, the device shall not place a call for vehicle service on
        that phase.
            Bit 7: Phase # = (phaseControlGroupNumber * 8)
            Bit 6: Phase # = (phaseControlGroupNumber * 8) - 1
            Bit 5: Phase # = (phaseControlGroupNumber * 8) - 2
            Bit 4: Phase # = (phaseControlGroupNumber * 8) - 3
            Bit 3: Phase # = (phaseControlGroupNumber * 8) - 4
            Bit 2: Phase # = (phaseControlGroupNumber * 8) - 5
            Bit 1: Phase # = (phaseControlGroupNumber * 8) - 6
            Bit 0: Phase # = (phaseControlGroupNumber * 8) - 7
        The device shall reset this object to ZERO when in BACKUP Mode. A
        write to this object shall reset the Backup timer to ZERO
        (see unitBackupTime).
    <Object Identifier> 1.3.6.1.4.1.1206.4.2.1.1.5.1.6
    <Object Type> C"
    ::= { phaseControlGroupEntry 6 }

--5.2.5.7   Phase Pedestrian Call Control
phaseControlGroupPedCall OBJECT-TYPE
    SYNTAX Integer32 (0..255)
    MAX-ACCESS read-write
    STATUS current
    DESCRIPTION "<Definition> This object is used to allow a remote entity to
        place calls for ped service in the device. When a bit = 1, the device
        shall place a call for ped service on that phase. When a bit = 0, the
        device shall not place a call for ped service on that phase.
            Bit 7: Phase # = (phaseControlGroupNumber * 8)
            Bit 6: Phase # = (phaseControlGroupNumber * 8) - 1
            Bit 5: Phase # = (phaseControlGroupNumber * 8) - 2
            Bit 4: Phase # = (phaseControlGroupNumber * 8) - 3
            Bit 3: Phase # = (phaseControlGroupNumber * 8) - 4
            Bit 2: Phase # = (phaseControlGroupNumber * 8) - 5
            Bit 1: Phase # = (phaseControlGroupNumber * 8) - 6
            Bit 0: Phase # = (phaseControlGroupNumber * 8) - 7
        The device shall reset this object to ZERO when in BACKUP Mode. A
        write to this object shall reset the Backup timer to ZERO
        (see unitBackupTime).
    <Object Identifier> 1.3.6.1.4.1.1206.4.2.1.1.5.1.7
    <Object Type> C"
    ::= { phaseControlGroupEntry 7 }

--5.2.6 Maximum Phase Sets
maxPhaseSets OBJECT-TYPE
    SYNTAX Integer32 (1..255)
    UNITS "set"
    MAX-ACCESS read-write
    STATUS current
    DESCRIPTION  "<Definition> The Maximum Number of Phase Sets this Controller
        Unit supports. This object indicates the maximum value for the
        phaseSetTable index phaseSetNumber.
    <Object Identifier> 1.3.6.1.4.1.1206.4.2.1.1.6
    <Object Type> S"
    ::= { phase 6 }

--5.2.7 Phase Set Table
phaseSetTable OBJECT-TYPE
    SYNTAX SEQUENCE OF PhaseSetEntry
    MAX-ACCESS not-accessible
    STATUS current
    DESCRIPTION "<Definition> A table containing Controller Unit phase
        parameters. The number of rows in this table is equal to the maxPhases
        object times the maxPhaseSets object.

        The first set in this table (phaseSetNumber = 1) shall match is corresponding objects in the phaseTable, unless explicitly defined. For example:
            phaseSetWalk.1.n = phaseWalk.n
            phaseSetPedestrianClear.1.n = phasePedestrianClear.n:
            phaseSetMinimumGreen.1.n = phaseMinimumGreen.n
			etc
            phaseSetPedClearDuringTransition.1.n = phasePedClearDuringTransition.n
    <TableType> static
    <Object Identifier> 1.3.6.1.4.1.1206.4.2.1.1.7"
    ::= { phase 7 }

phaseSetEntry OBJECT-TYPE
    SYNTAX PhaseSetEntry
    MAX-ACCESS not-accessible
    STATUS current
    DESCRIPTION "<Definition> Parameters for a set of Controller Unit phases.
    <Object Identifier> 1.3.6.1.4.1.1206.4.2.1.1.7.1"
    INDEX { phaseSetNumber, phaseNumber }
    ::= { phaseSetTable 1 }
 
PhaseSetEntry ::= SEQUENCE { 
    phaseSetNumber                     Integer32,
    phaseSetWalk                       Integer32,
    phaseSetPedestrianClear            Integer32,
    phaseSetMinimumGreen               Integer32,
    phaseSetPassage                    Integer32,
    phaseSetMaximum1                   Integer32,
    phaseSetMaximum2                   Integer32,
    phaseSetYellowChange               Integer32,
    phaseSetRedClear                   Integer32,
    phaseSetRedRevert                  Integer32,
    phaseSetAddedInitial               Integer32,
    phaseSetMaximumInitial             Integer32,
    phaseSetTimeBeforeReduction        Integer32,
    phaseSetCarsBeforeReduction        Integer32,
    phaseSetTimeToReduce               Integer32,
    phaseSetReduceBy                   Integer32,
    phaseSetMinimumGap                 Integer32,
    phaseSetDynamicMaxLimit            Integer32,
    phaseSetDynamicMaxStep             Integer32,
    phaseSetOptions                    Integer32,
    phaseSetMaximum3                   Integer32,
    phaseSetPedClearDuringVehicleClear Integer32,
    phaseSetPedServiceLimit            Integer32,
    phaseSetDontWalkRevert             Integer32,
    phaseSetPedAlternateClearance      Integer32,
    phaseSetPedAlternateWalk           Integer32,
    phaseSetPedAdvanceWalkTime         Integer32, 
    phaseSetPedDelayTime               Integer32, 
    phaseSetAdvWarnGrnStartTime        Integer32,
    phaseSetAdvWarnRedStartTime        Integer32,
    phaseSetAltMinTimeTransition       Integer32,
    phaseSetWalkDuringTransition       Integer32,
    phaseSetPedClearDuringTransition   Integer32    }

--5.2.7.1   Phase Set Number
phaseSetNumber OBJECT-TYPE
    SYNTAX Integer32 (1..255)
    UNITS "set"
    MAX-ACCESS not-accessible
    STATUS current
    DESCRIPTION "<Definition> The set number for objects in this row. This
        value shall not exceed the maxPhaseSets object value.
    <Object Identifier> 1.3.6.1.4.1.1206.4.2.1.1.7.1.1"
    ::= { phaseSetEntry 1 }

--5.2.7.2   Phase Set Walk Parameter
phaseSetWalk OBJECT-TYPE
    SYNTAX Integer32 (0..255)
    UNITS "second"
    MAX-ACCESS read-write
    STATUS current
    DESCRIPTION "<Definition> Phase Walk Parameter in seconds. This shall
        control the amount of time the Walk indication shall be displayed.
        This parameter shall be used regardless whether the pedestrian
        indication associated with this phase is for a ped-only phase or for
        a pedestrian indication that runs parallel to a vehicle phase.
    <Object Identifier> 1.3.6.1.4.1.1206.4.2.1.1.7.1.2
    <Object Type> P"
    REFERENCE "NEMA TS 2 Clause 3.5.3.1 and 3.5.3.2.2.a"
    ::= { phaseSetEntry 2 }


--5.2.7.3   Phase Set Pedestrian Clear Parameter
phaseSetPedestrianClear OBJECT-TYPE
    SYNTAX Integer32 (0..255)
    UNITS "second"
    MAX-ACCESS read-write
    STATUS current
    DESCRIPTION "<Definition> Phase Pedestrian Clear Parameter in seconds.
        This shall control the duration of the Pedestrian Clearance output
        (if present) and the flashing period of the Don't Walk output.

        This parameter shall be used regardless whether the pedestrian
        indication associated with this phase is for a ped-only phase or for
        a pedestrian indication that runs parallel to a vehicle phase.
    <Object Identifier> 1.3.6.1.4.1.1206.4.2.1.1.7.1.3
    <Object Type> P"
    REFERENCE "NEMA TS 2 Clause 3.5.3.1 and 3.5.3.2.2.b"
    ::= { phaseSetEntry 3 }


--5.2.7.4   Phase Set Minimum Green Parameter
phaseSetMinimumGreen OBJECT-TYPE
    SYNTAX Integer32 (0..255)
    UNITS "second"
    MAX-ACCESS read-write
    STATUS current
    DESCRIPTION "<Definition> Phase Minimum Green Parameter in seconds (NEMA
        TS 2 range: 1-255 sec). The first timed portion of the Green interval
        which may be set in consideration of the storage of vehicles between
        the zone of detection for the approach vehicle detector(s) and the
        stop line.
    <Object Identifier> 1.3.6.1.4.1.1206.4.2.1.1.7.1.4
    <Object Type> P"
    REFERENCE "NEMA TS 2 Clause 3.5.3.1 and 3.5.3.2.1.a.(1)"
    ::= { phaseSetEntry 4 }


--5.2.7.5   Phase Set Passage Parameter
phaseSetPassage OBJECT-TYPE
    SYNTAX Integer32 (0..255)
    UNITS "decisecond"
    MAX-ACCESS read-write
    STATUS current
    DESCRIPTION "<Definition> Phase Passage Parameter in tenth seconds
        (0-25.5 sec). Passage Time, Vehicle Interval, Preset Gap, Vehicle
        Extension: the extensible portion of the Green shall be a function of
        vehicle actuations that occur during the Green interval. The phase
        shall remain in the extensible portion of the Green interval as long
        as the passage timer is not timed out. The timing of this portion of
        the green interval shall be reset with each subsequent vehicle
        actuation and shall not commence to time again until the vehicle
        actuation is removed or the maximum green timer has expired.
    <Object Identifier> 1.3.6.1.4.1.1206.4.2.1.1.7.1.5
    <Object Type> P"
    REFERENCE "NEMA TS 2 Clause 3.5.3.1 and 3.5.3.2.1.a.(2)"
    ::= { phaseSetEntry 5 }

--5.2.7.6   Phase Set Maximum Green 1 Parameter
phaseSetMaximum1 OBJECT-TYPE
    SYNTAX Integer32 (0..999)
    UNITS "second"
    MAX-ACCESS read-write
    STATUS current
    DESCRIPTION "<Definition> Phase Maximum 1 Parameter in seconds (NEMA TS 2
        range: 1-255 sec). This time setting shall determine the maximum
        length of time this phase may be held in Green in the presence of a
        serviceable conflicting call. In the absence of a serviceable
        conflicting call, the Maximum Green timer shall be held reset unless
        Max Vehicle Recall is enabled for this phase. This is the default
        maximum value to use. It may be overridden via an external input,
        coordMaximumMode, or other method.
    <Object Identifier> 1.3.6.1.4.1.1206.4.2.1.1.7.1.6
    <Object Type> P"
    REFERENCE "NEMA TS 2 Clause 3.5.3.1, 3.5.3.2.1.a.(3) and 3.5.3.5"
    ::= { phaseSetEntry 6 }

--5.2.7.7   Phase Set Maximum Green 2 Parameter
phaseSetMaximum2 OBJECT-TYPE
    SYNTAX Integer32 (0..999)
    UNITS "second"
    MAX-ACCESS read-write
    STATUS current
    DESCRIPTION "<Definition> Phase Maximum 2 Parameter in seconds (NEMA TS 2
        range: 1-255 sec). This time setting shall determine the maximum
        length of time this phase may be held in Green in the presence of a
        serviceable conflicting call. In the absence of a serviceable
        conflicting call the Maximum Green timer shall be held reset unless
        Max Vehicle Recall is enabled for this phase. This may be implemented
        as the max green timer via an external input, coordMaximumMode or
        other method.
    <Object Identifier> 1.3.6.1.4.1.1206.4.2.1.1.7.1.7
    <Object Type> P"
    REFERENCE "NEMA TS 2 Clause 3.5.3.1, 3.5.3.2.1.a.(3), 3.5.3.5 
     and 3.5.4.1 (7)"
    ::= { phaseSetEntry 7 }

--5.2.7.8   Phase Set Yellow Change Parameter
phaseSetYellowChange OBJECT-TYPE
    SYNTAX Integer32 (0..255)
    UNITS "decisecond"
    MAX-ACCESS read-write
    STATUS current
    DESCRIPTION "<Definition> Phase Yellow Change Parameter in tenth seconds
        (NEMA TS 2 range: 3-25.5 sec). Following the Green interval of each
        phase the CU shall provide a Yellow Change interval which is timed
        according to the Yellow Change parameter for that phase.
    <Object Identifier> 1.3.6.1.4.1.1206.4.2.1.1.7.1.8
    <Object Type> P"
    REFERENCE "NEMA TS 2 Clause 3.5.3.1 and 3.5.3.2.5.a"
    ::= { phaseSetEntry 8 }

--5.2.7.9   Phase Set Red Clearance Parameter
phaseSetRedClear OBJECT-TYPE
    SYNTAX Integer32 (0..255)
    UNITS "decisecond"
    MAX-ACCESS read-write
    STATUS current
    DESCRIPTION "<Definition> Phase Red Clearance Parameter in tenth seconds
        (0-25.5 sec). Following the Yellow Change interval for each phase, the
        CU shall provide a Red Clearance interval which is timed according to
        the Red Clearance parameter for that phase.
    <Object Identifier> 1.3.6.1.4.1.1206.4.2.1.1.7.1.9
    <Object Type> P"
    REFERENCE "NEMA TS 2 Clause 3.5.3.1 and 3.5.3.2.5.b"
    ::= { phaseSetEntry 9 }

--5.2.7.10  Phase Set Red Revert Parameter
phaseSetRedRevert OBJECT-TYPE
    SYNTAX Integer32 (0..255)
    UNITS "decisecond"
    MAX-ACCESS read-write
    STATUS current
    DESCRIPTION "<Definition> Red revert time parameter in tenths of seconds
        (0-25.5 sec). A minimum RED indication to be timed following the
        Yellow Change interval and prior to the next display of Green on the
        same signal output driver group.

        The unitRedRevert parameter shall act as a minimum red revert time for
        all signal displays. The phaseSetRedRevert parameter may increase the red
        revert time for a specific phase. If the phaseSetRedRevert parameter is
        less than the unitRedRevert the unitRedRevert time shall be used.
    <Object Identifier> 1.3.6.1.4.1.1206.4.2.1.1.7.1.10
    <Object Type> P"
    ::= { phaseSetEntry 10 }

--5.2.7.11  Phase Set Added Initial Parameter
phaseSetAddedInitial OBJECT-TYPE
    SYNTAX Integer32 (0..255)
    UNITS "decisecond"
    MAX-ACCESS read-write
    STATUS current
    DESCRIPTION "<Definition> Phase Added Initial Parameter in tenths of
        seconds (0-25.5 sec). Added Initial parameter (Seconds / Actuation)
        shall determine the time by which the variable initial time period
        will be increased from zero with each vehicle actuation received
        during the associated phase Yellow and Red intervals.
    <Object Identifier> 1.3.6.1.4.1.1206.4.2.1.1.7.1.11
    <Object Type> P"
    REFERENCE "NEMA TS 2 Clause 3.5.3.1 and 3.5.3.2.1.b.(1).(b)"
    ::= { phaseSetEntry 11 }

--5.2.7.12  Phase Set Maximum Initial Parameter
phaseSetMaximumInitial OBJECT-TYPE
    SYNTAX Integer32 (0..255)
    UNITS "second"
    MAX-ACCESS read-write
    STATUS current
    DESCRIPTION "<Definition> Phase Maximum Initial Parameter in seconds
        (0-255 sec). The maximum value of the variable initial timing period.
        Variable Initial timing shall equal the lesser of [added initial
        (seconds / actuation) * number of actuations] or [ Max Initial ].
        The variable initial time shall not be less than Minimum Green.
    <Object Identifier> 1.3.6.1.4.1.1206.4.2.1.1.7.1.12
    <Object Type> P"
    REFERENCE "NEMA TS 2 Clause 3.5.3.2.1.b.(1).(c)"
    ::= { phaseSetEntry 12 }

--5.2.7.13  Phase Set Time Before Reduction Parameter
phaseSetTimeBeforeReduction OBJECT-TYPE
    SYNTAX Integer32 (0..255)
    UNITS "second"
    MAX-ACCESS read-write
    STATUS current
    DESCRIPTION "<Definition> Phase Time Before Reduction (TBR) Parameter in
        seconds (0-255 sec). The Time Before Reduction period shall begin
        when the phase is Green and there is a serviceable conflicting call.
        If the serviceable conflicting call is removed before completion of
        this time (or time to reduce), the timer shall reset. Upon completion
        of the TBR period or the CarsBeforeReduction (CBR) parameter is
        satisfied, whichever occurs first, the linear reduction of the
        allowable gap from the Passage Time shall begin.
    <Object Identifier> 1.3.6.1.4.1.1206.4.2.1.1.7.1.13
    <Object Type> P"
    REFERENCE "NEMA TS 2 Clause 3.5.3.1 and 3.5.3.2.1.b.(2)"
    ::= { phaseSetEntry 13 }

--5.2.7.14  Phase Set Cars Before Reduction Parameter
phaseSetCarsBeforeReduction OBJECT-TYPE
    SYNTAX Integer32 (0..255)
    UNITS "vehicle"
    MAX-ACCESS read-write
    STATUS current
    DESCRIPTION "<Definition> Phase Cars Before Reduction (CBR) Parameter
        (0-255 vehicles). When the phase is Green and the sum of the cars
        waiting (vehicle actuations during Yellow & Red intervals) on
        serviceable conflicting phases equals or exceeds the CBR parameter or
        the Time Before Reduction (TBR) parameter is satisfied, whichever
        occurs first, the linear reduction of the allowable gap from the
        Passage Time shall begin.
    <Object Identifier> 1.3.6.1.4.1.1206.4.2.1.1.7.1.14
    <Object Type> P"
    ::= { phaseSetEntry 14 }

--5.2.7.15  Phase Set Time To Reduce Parameter
phaseSetTimeToReduce OBJECT-TYPE
    SYNTAX Integer32 (0..255)
    UNITS "second"
    MAX-ACCESS read-write
    STATUS current
    DESCRIPTION "<Definition> Phase Time To Reduce Parameter in seconds
        (0-255 sec). This parameter shall control the rate of reduction of the
        allowable gap between the Passage Time and Minimum Gap setting.
    <Object Identifier> 1.3.6.1.4.1.1206.4.2.1.1.7.1.15
    <Object Type> P"
    REFERENCE "NEMA TS 2 Clause 3.5.3.1 and 3.5.3.2.1.b.(2)"
    ::= { phaseSetEntry 15 }
 
--5.2.7.16  Phase Set Reduce By Parameter
phaseSetReduceBy OBJECT-TYPE
    SYNTAX Integer32 (0..255)
    UNITS "decisecond"
    MAX-ACCESS read-write
    STATUS current
    DESCRIPTION "<Definition> This object may be used for volume density gap
        reduction as an alternate to the linear reduction defined by NEMA TS 1
        and TS 2. It contains the tenths of seconds to reduce the gap by
        (0.0 - 25.5 seconds). The frequency of reduction shall produce the
        Minimum Gap after a time equal to the 'phaseSetTimeToReduce' object.
    <Object Identifier> 1.3.6.1.4.1.1206.4.2.1.1.7.1.16
    <Object Type> P"
    ::= { phaseSetEntry 16 }

--5.2.7.17  Phase Set Minimum Gap Parameter
phaseSetMinimumGap OBJECT-TYPE
    SYNTAX Integer32 (0..255)
    UNITS "decisecond"
    MAX-ACCESS read-write
    STATUS current
    DESCRIPTION "<Definition> Phase Minimum Gap Parameter in tenth seconds
        (0-25.5 sec). The reduction of the allowable gap shall continue until
        the gap reaches a value equal to or less than the minimum gap as set
        on the Minimum Gap control after which the allowable gap shall remain
        fixed at the values set on the Minimum Gap control.
    <Object Identifier> 1.3.6.1.4.1.1206.4.2.1.1.7.1.17
    <Object Type> P"
    REFERENCE "NEMA TS 2 Clause 3.5.3.1 and 3.5.3.2.1.b.(2)"
    ::= { phaseSetEntry 17 }

--5.2.7.18  Phase Set Dynamic Max Limit
phaseSetDynamicMaxLimit OBJECT-TYPE
    SYNTAX Integer32 (0..255)
    UNITS "second"
    MAX-ACCESS read-write
    STATUS current
    DESCRIPTION "<Definition> This object shall determine either the upper or
        lower limit of the running max in seconds (0-255 sec) during dynamic
        max operation. The normal maximum (i.e. phaseSetMaximum1,
		phaseSetMaximum2, etc.) shall determine the other limit as follows:
        When this value is larger than the normal maximum, it is the upper limit.
        When this value is smaller than the normal maximum, it is the lower limit.
        Setting phaseSetDynamicMaxLimit greater than zero enables dynamic max
            operation with the normal maximum used as the initial maximum
            setting. See phaseSetDynamicMaxStep for details on dynamic max operation.

        Max or a failed detector that is assigned to the associated
            phase shall disable dynamic max operation for the phase.
    <Object Identifier> 1.3.6.1.4.1.1206.4.2.1.1.7.1.18
    <Object Type> P"
    ::= { phaseSetEntry 18 }

--5.2.7.19  Phase Set Dynamic Max Step
phaseSetDynamicMaxStep OBJECT-TYPE
    SYNTAX Integer32 (0..255)
    UNITS "decisecond"
    MAX-ACCESS read-write
    STATUS current
    DESCRIPTION "<Definition> This object shall determine the automatic adjustment
        to the running max in tenths of seconds (0-25.5). When an ASC decides
        to adjust the running max for the phase, the value of this object shall
        be added or subtracted to the running max per cycle.
    <Object Identifier> 1.3.6.1.4.1.1206.4.2.1.1.7.1.19
    <Object Type> P"
    ::= { phaseSetEntry 19 }

-- Note: There is no object corresponding to phaseStartUp in phaseSetTable.

--5.2.7.20  Phase Set Options
phaseSetOptions OBJECT-TYPE
    SYNTAX Integer32 (0..65535)
    MAX-ACCESS read-write
    STATUS current
    DESCRIPTION "<Definition>Optional phase functions
        (0 = False/Disabled, 1 = True/Enabled)
    Bit 15: Not used (AddedInitialCalculation only in the object phaseOptions)
    Bit 14: Conditional Service Enable - in multi-ring configurations when set
        to 1 causes a gapped/maxed phase to conditionally service a preceding
        actuated vehicle phase when sufficient time remains before max time out
        of the phase(s) not prepared to terminate. Support is optional.
        REFERENCE NEMA TS 2 Clause 3.5.3.9
    Bit 13: Actuated Rest-in-Walk - when set to 1 causes an actuated phase to
        Rest-in-Walk when there is no serviceable conflicting call at the end
        of Walk Timing or if Max Vehicle Recall is enabled.
    Bit 12: Reserved -- Not Used (Guaranteed Passage only in the object phaseOptions)
    Bit 11: Simultaneous Gap Disable - in multi-ring configurations when set
        to 1 disables a gapped out phase from reverting to the extensible
        portion. Support is optional.
        REFERENCE NEMA TS 2 Clause 3.5.5.3
    Bit 10: Dual Entry Phase - in multi-ring configurations when set to 1
        causes the phase to become active upon entry into a concurrency group
        (crossing a barrier) when no calls exist in its ring within its
        concurrency group.
        REFERENCE NEMA TS 2 Clause 3.5.5.3
    Bit 9: Soft Vehicle Recall - when set to 1 causes a call on a phase when
        all conflicting phases are in green dwell or red dwell and there are
        no serviceable conflicting calls. Support is optional.
    Bit 8: Ped. Recall - when set to 1 causes a recurring pedestrian demand
        which shall function in the same manner as an external pedestrian call
        except that it shall not recycle the pedestrian service until a
        conflicting phase is serviced.
        REFERENCE NEMA TS 2 Clause 3.5.3.7
    Bit 7: Max Vehicle Recall - when set to 1 causes a call on a phase such
        that the timing of the Green interval for that phase shall be extended
        to Maximum Green time.
        REFERENCE NEMA TS 2 Clause 3.5.3.5
    Bit 6: Min. Vehicle Recall - when set to 1 causes recurring demand for
        vehicle service on the phase when that phase is not in its Green
        interval.
        REFERENCE NEMA TS 2 Clause 3.5.3.6
    Bit 5: Non Lock Detector Memory - when set to 0 will cause the call to be
        locked at the beginning of the yellow interval. When set to 1 call
        locking will depend on the detectorOptions object.
        REFERENCE NEMA TS 2 Clause 3.5.3.4
    Bit 4: Non-Actuated 2 - when set to 1 causes a phase to respond to the
        Call To Non-Actuated 2 input (if present) or other method. Support
        is optional.
        REFERENCE NEMA TS 2 Clause 3.5.5.5.8
    Bit 3: Non-Actuated 1 - when set to 1 causes a phase to respond to the
        Call To Non-Actuated 1 input (if present) or other method. Support is
        optional.
        REFERENCE NEMA TS 2 Clause 3.5.5.5.8
    Bit 2: Reserved --Not used (Automatic Flash Exit Phase only in object phaseOptions)
    Bit 1: Reserved --Not used (Automatic Flash Entry only in the object phaseOptions)
    Bit 0: Reserved --Not Used (Enabled Phase only in the object phaseOptions)

    A SET of a 'reserved' bit to a value other than zero (0) shall return a badValue(3) error.
    <Object Identifier> 1.3.6.1.4.1.1206.4.2.1.1.7.1.20
    <Object Type> P"
    ::= { phaseSetEntry 20 }

-- Note: There is no object corresponding to phaseRing in phaseSetTable

-- Note: There is no object corresponding to phaseConcurrency in phaseSetTable

--5.2.7.21  Phase Set Maximum Green 3 Parameter
phaseSetMaximum3 OBJECT-TYPE
    SYNTAX Integer32 (0..999)
    UNITS "second"
    MAX-ACCESS read-write
    STATUS current
    DESCRIPTION "<Definition> Phase Maximum 3 Parameter in seconds. This time
        setting shall determine the maximum length of time this phase may be
        held in Green in the presence of a serviceable conflicting call. In
        the absence of a serviceable conflicting call, the Maximum Green timer
        shall be held reset unless Max Vehicle Recall is enabled for this
        phase. This may be implemented as the max green timer via an external
        input, coordMaximumMode, or other method.
    <Object Identifier> 1.3.6.1.4.1.1206.4.2.1.1.7.1.21
    <Object Type> P"
    ::= { phaseSetEntry 21 }

--5.2.7.22  Phase Set Ped Clearance During Vehicle Clearance
phaseSetPedClearDuringVehicleClear OBJECT-TYPE
    SYNTAX Integer32 (0..255)
    UNITS "decisecond"
    MAX-ACCESS read-write
    STATUS current
    DESCRIPTION "<Definition> The amount of time that the pedestrian clearance
        may extend into the vehicle clearance time (yellow and red) for a
        phase. This parameter is expressed in 0.1 second increments ranging
        from 0.0 to 25.5 seconds.
    <Object Identifier> 1.3.6.1.4.1.1206.4.2.1.1.7.1.22
    <Object Type> P"
    ::= { phaseSetEntry 22 }

--5.2.7.23  Phase Set Pedestrian Service Limit
phaseSetPedServiceLimit OBJECT-TYPE
    SYNTAX Integer32 (0..255)
    MAX-ACCESS read-write
    STATUS current
    DESCRIPTION "<Definition> This parameter indicates whether and how many
        times this phase is allowed to recycle the pedestrian movement during
        a cycle. This parameter is typically used for ped-only, signalized intersections
        (mostly mid-block) that are within a coordinated roadway. If set to
        '1', no recycle is allowed and the pedestrian movement can be shown
        only up to once. If set to '2', the pedestrian movement can be shown
        up to twice during a cycle, etc. A value of zero means there is no limit. 
    <Object Identifier> 1.3.6.1.4.1.1206.4.2.1.1.7.1.23
    <Object Type> P"
    DEFVAL { 0 }
    ::= { phaseSetEntry 23 }

--5.2.7.24  Phase Set Pedestrian Don't Walk Revert Parameter
phaseSetDontWalkRevert OBJECT-TYPE
    SYNTAX Integer32 (0..255)
    UNITS "decisecond"
    MAX-ACCESS read-write
    STATUS current
    DESCRIPTION "<Definition> Don't Walk revert time parameter in tenth
        seconds. A minimum DON'T WALK indication to be timed following the
        pedestrian clearance interval prior to the next WALK indication on
        the same signal output driver group.
    <Object Identifier> 1.3.6.1.4.1.1206.4.2.1.1.7.1.24
    <Object Type> P"
    ::= { phaseSetEntry 24 }

--5.2.7.25  Phase Set Alternate Pedestrian Clearance Time Parameter
phaseSetPedAlternateClearance OBJECT-TYPE
    SYNTAX Integer32 (0..255)
    UNITS "second"
    MAX-ACCESS read-write
    STATUS current
    DESCRIPTION "<Definition> An alternate (replacement) time, in seconds, for
        the duration of the pedestrian clearance output (if present) and the
        flashing period of the DON'T WALK output.

        This parameter may be used for a parallel pedestrian indication in
        conjunction with a vehicle phase or with a ped-only phase.
    <Object Identifier> 1.3.6.1.4.1.1206.4.2.1.1.7.1.25
    <Object Type> P"
    ::= { phaseSetEntry 25 }

--5.2.7.26  Phase Set Alternate Pedestrian Walk Time Parameter
phaseSetPedAlternateWalk OBJECT-TYPE
    SYNTAX Integer32 (0..255)
    UNITS "second"
    MAX-ACCESS read-write
    STATUS current
    DESCRIPTION "<Definition> An alternate (replacement) time, in seconds, for
        a pedestrian walk. This shall control the amount of time the Walk
        indication shall be displayed.

        This parameter may be used for a parallel pedestrian indication in
        conjunction with a vehicle phase or with a ped-only phase.
    <Object Identifier> 1.3.6.1.4.1.1206.4.2.1.1.7.1.26
    <Object Type> P"
    ::= { phaseSetEntry 26 }

--5.2.2.27  Phase Set Pedestrian Advance Walk Time Parameter
phaseSetPedAdvanceWalkTime OBJECT-TYPE
    SYNTAX Integer32 (0..255)
    UNITS "decisecond"
    MAX-ACCESS read-write
    STATUS current
    DESCRIPTION "<Definition> The amount of time, in tenths of a second from
        0 to 25.5 seconds, that the phase's pedestrian Walk
        indication starts before the start of the phase's vehicle GREEN indication.
        
        This parameter is used as the result of a pedestrian detector input as configured in pedestrianSetDetectorOptions or if pedestrian recall is enabled.
    <Object Identifier> 1.3.6.1.4.1.1206.4.2.1.1.7.1.27
    <Object Type> P"
    DEFVAL { 0 }
    ::= { phaseSetEntry 27 }

--5.2.2.28  Phase Set Pedestrian Delay Walk Time Parameter
phaseSetPedDelayTime OBJECT-TYPE
    SYNTAX Integer32 (0..255)
    UNITS "decisecond"
    MAX-ACCESS read-write
    STATUS current
    DESCRIPTION "<Definition> The amount of time, in tenths of a second from
        0 to 25.5 seconds, that the phase's pedestrian Walk
        indication starts after the start of the phase's vehicle GREEN indication. 
        
        This parameter is used as result of a pedestrian detector input.
    <Object Identifier> 1.3.6.1.4.1.1206.4.2.1.1.7.1.28
    <Object Type> P"
    DEFVAL { 0 }
    ::= { phaseSetEntry 28 }

--5.2.7.29  Phase Set Advance Green Indication Start Time Parameter
phaseSetAdvWarnGrnStartTime OBJECT-TYPE
    SYNTAX Integer32 (0..255)
    UNITS "decisecond"
    MAX-ACCESS read-write
    STATUS current
    DESCRIPTION "<Definition> The amount of time, in tenths of a second for a
        period of 0.0 to 25.5 seconds, that an advance warning signal
        indication is displayed before the start of phase Green. The warning
        signal is placed upstream of the phase's approach and indicates that
        the phase's GREEN indication is about to start or has started.
        The value of this object should not exceed the total amount of
        clearance time of the phase(s) that is being terminated prior to the
        start of this phase.

        Note: The Advance Warning Green terminates at the end of the green.
    <Object Identifier> 1.3.6.1.4.1.1206.4.2.1.1.7.1.29
    <Object Type> P"
    ::= { phaseSetEntry 29 }

--5.2.7.30  Phase Set Advance Red Indication Start Time Parameter
phaseSetAdvWarnRedStartTime OBJECT-TYPE
    SYNTAX Integer32 (0..255)
    UNITS "decisecond"
    MAX-ACCESS read-write
    STATUS current
    DESCRIPTION "<Definition> The amount of time, in tenths of a second for a
        range of 0.0 to 25.5 seconds, prior to the start of the phase's RED
        indication that an advance warning signal, placed upstream of the
        phase's approach, turns on.

        Note: The Advance Warning Red terminates at the end of Red.
    <Object Identifier> 1.3.6.1.4.1.1206.4.2.1.1.7.1.30
    <Object Type> P"
    ::= { phaseSetEntry 30 }

--5.2.7.31  Phase Set Alternate Minimum Green Time During Transitions
phaseSetAltMinTimeTransition OBJECT-TYPE
    SYNTAX Integer32 (0..255)
    UNITS "second"
    MAX-ACCESS read-write
    STATUS current
    DESCRIPTION "<Definition> This object indicates the alternate minimum green
        time that is used during transitions, in seconds from 1 to 255 seconds.
        This object can be applied during transitions or signal priority. A
        value of 0 indicates that this object is not used during transitions.
        This value shall not exceed phaseSetMinimumGreen for this phase.
    <Object Identifier> 1.3.6.1.4.1.1206.4.2.1.1.7.1.31
    <Object Type> P"
    DEFVAL { 0 }
    ::= { phaseSetEntry 31 }

--5.2.2.32  Phase Set Alternate Walk Time During Transitions
phaseSetWalkDuringTransition OBJECT-TYPE
    SYNTAX Integer32 (0..255)
    UNITS "second"
    MAX-ACCESS read-write
    STATUS current
    DESCRIPTION "<Definition> This object indicates the alternate walk time that is used during transitions, in seconds from 1 to 255
        seconds. This object can be applied during transitions or signal priority. A value of zero indicates that this object is not used during
        transitions. This value shall not exceed phaseSetWalk.
    <Object Identifier> 1.3.6.1.4.1.1206.4.2.1.1.7.1.32
    <Object Type> P"
    DEFVAL { 0 }
    ::= { phaseSetEntry 32 }

--5.2.2.33  Phase Set Alternate Pedestrian Clearance Time During Transitions
phaseSetPedClearDuringTransition OBJECT-TYPE
    SYNTAX Integer32 (0..255)
    UNITS "second"
    MAX-ACCESS read-write
    STATUS current
    DESCRIPTION "<Definition> This object indicates the alternate minimum pedestrian clearance time walk time that is used during transitions, in seconds from 1 to 255 seconds. This object can be applied during transitions or signal priority. A value of zero indicates that this object is not used during transitions. This value shall not exceed phaseSetPedestrianClear.
    <Object Identifier> 1.3.6.1.4.1.1206.4.2.1.1.7.1.33
    <Object Type> P"
    DEFVAL { 0 }
    ::= { phaseSetEntry 33 }

--5.3   Detector Parameters
detector OBJECT IDENTIFIER 
    ::= { asc 2 }

-- This defines a node for supporting detector objects.

--5.3.1 Maximum Vehicle Detectors
maxVehicleDetectors OBJECT-TYPE
    SYNTAX Integer32 (1..255)
    UNITS "detector"
    MAX-ACCESS read-only
    STATUS current
    DESCRIPTION "<Definition> The Maximum Number of Vehicle Detectors this
        Controller Unit supports. This object indicates the maximum rows
        which shall appear in the vehicleDetectorTable object.
    <Object Identifier> 1.3.6.1.4.1.1206.4.2.1.2.1
    <Object Type> S"
    ::= { detector 1 }

--5.3.2 Vehicle Detector Parameter Table
vehicleDetectorTable OBJECT-TYPE
    SYNTAX SEQUENCE OF VehicleDetectorEntry
    MAX-ACCESS not-accessible
    STATUS current
    DESCRIPTION "<Definition> A table containing Controller Unit vehicle
        detector parameters. The number of rows in this table is equal to the
        maxVehicleDetectors object.

        The objects in this table correspond to the matching objects in the
        first set (vehicleDetectorSetNumber = 1) of the vehicleDetectorSetTable.
    <TableType> static
    <Object Identifier> 1.3.6.1.4.1.1206.4.2.1.2.2"
    ::= { detector 2 }

vehicleDetectorEntry OBJECT-TYPE
    SYNTAX VehicleDetectorEntry
    MAX-ACCESS not-accessible
    STATUS current
    DESCRIPTION "<Definition> Parameters for a specific Controller Unit
        detector.
    <Object Identifier> 1.3.6.1.4.1.1206.4.2.1.2.2.1"
    INDEX   { vehicleDetectorNumber }
    ::= { vehicleDetectorTable 1 }

VehicleDetectorEntry ::= SEQUENCE {
    vehicleDetectorNumber                Integer32,
    vehicleDetectorOptions               Integer32,
    vehicleDetectorDescription           SnmpAdminString,
    vehicleDetectorCallPhase             Integer32,
    vehicleDetectorSwitchPhase           Integer32,
    vehicleDetectorDelay                 Integer32,
    vehicleDetectorExtend                Integer32,
    vehicleDetectorQueueLimit            Integer32,
    vehicleDetectorNoActivity            Integer32,
    vehicleDetectorMaxPresence           Integer32,
    vehicleDetectorErraticCounts         Integer32,
    vehicleDetectorFailTime              Integer32,
    vehicleDetectorAlarms                Integer32,
    vehicleDetectorReportedAlarms        Integer32,
    vehicleDetectorReset                 Integer32, 
    vehicleDetectorOptions2              Integer32,
    vehicleDetectorPairedDetector        Integer32,
    vehicleDetectorPairedDetectorSpacing Integer32,
    vehicleDetectorAvgVehicleLength      Integer32,
    vehicleDetectorLength                Integer32,
    vehicleDetectorTravelMode            INTEGER }

--5.3.2.1   Vehicle Detector Number
vehicleDetectorNumber OBJECT-TYPE
    SYNTAX Integer32 (1..255)
    UNITS "detector"
    MAX-ACCESS not-accessible
    STATUS current
    DESCRIPTION "<Definition> The vehicle detector number for objects in this
        row. The value shall not exceed the maxVehicleDetectors object value.
    <Object Identifier> 1.3.6.1.4.1.1206.4.2.1.2.2.1.1"
    ::= { vehicleDetectorEntry 1 }

--5.3.2.2   Vehicle Detector Options Parameter
vehicleDetectorOptions OBJECT-TYPE
    SYNTAX Integer32 (0..255)
    MAX-ACCESS read-write
    STATUS current
    DESCRIPTION "<Definition> Vehicle Detector Options Parameter as follows
        (0=Disabled, 1=Enabled):
    Bit 7: Call - if Enabled, the CU shall place a demand for vehicular
        service on the assigned phase when the phase is not timing the green
        interval and an actuation is present.
    Bit 6: Queue - if Enabled, the CU shall extend the green interval of the
        assigned phase until a gap occurs (no actuation) or until the green
        has been active longer than the vehicleDetectorQueueLimit time.
        This is optional.
    Bit 5: AddedInitial - if Enabled, the CU shall accumulate detector
        actuation counts for use in the added initial calculations. Counts
        shall be accumulated from the beginning of the yellow interval to the
        beginning of the green interval.
    Bit 4: Passage - if Enabled, the CU shall maintain a reset to the
        associated phase passage timer for the duration of the detector
        actuation when the phase is green.
    Bit 3: Red Lock Call - if Enabled, the detector will lock a call to the
        assigned phase if an actuation occurs while the phase is not timing
        Green or Yellow. This mode is optional.
    Bit 2: Yellow Lock Call - if Enabled, the detector will lock a call to
        the assigned phase if an actuation occurs while the phase is not
        timing Green.
    Bit 1: Reserved. This bit was previously used to enable occupancy detection.
    Bit 0: Reserved. This bit was previously used to enable volume detection. 

    A SET of both bits 2 & 3 = 1 shall result in bit 2=1 and bit 3=0.
    <Object Identifier> 1.3.6.1.4.1.1206.4.2.1.2.2.1.2
    <Object Type> P"
    ::= { vehicleDetectorEntry 2}

--5.3.2.3  Vehicle Detector Description
vehicleDetectorDescription OBJECT-TYPE
    SYNTAX SnmpAdminString 
    MAX-ACCESS read-write
    STATUS current
    DESCRIPTION "<Definition> A textual string indicate a user description for the vehicle detector (e.g. location). This value is the same for all vehicle detector sets. 
    <Object Identifier> 1.3.6.1.4.1.1206.4.2.1.2.2.1.3
    <Object Type> P"
    ::= { vehicleDetectorEntry 3 }

--5.3.2.4   Vehicle Detector Call Phase Parameter
vehicleDetectorCallPhase OBJECT-TYPE
    SYNTAX Integer32 (0..255)
    UNITS "phase"
    MAX-ACCESS read-write
    STATUS current
    DESCRIPTION "<Definition> This object contains assigned phase number for the detector input associated with this row. A value of zero indicates this detector does not call a phase. The value shall not exceed the value of maxPhases.
    <Object Identifier> 1.3.6.1.4.1.1206.4.2.1.2.2.1.4
    <Object Type> P"
    REFERENCE "NEMA TS 2 Clause 3.5.5.5.4 and 3.5.5.5.5" 
    ::= { vehicleDetectorEntry 4 }

--5.3.2.5   Vehicle Detector Switch Phase Parameter
vehicleDetectorSwitchPhase OBJECT-TYPE
    SYNTAX Integer32 (0..255)
    UNITS "phase"
    MAX-ACCESS read-write
    STATUS current
    DESCRIPTION "<Definition> Detector Switch Phase Parameter (i.e., Phase
        Number). The phase to which a vehicle detector actuation shall be
        switched when the assigned phase is Yellow or Red and the Switch Phase
        is Green. The value shall not exceed the value of maxPhases.
    <Object Identifier> 1.3.6.1.4.1.1206.4.2.1.2.2.1.5
    <Object Type> P"
    REFERENCE "NEMA TS 2 Clause 3.5.5.5.4.c"
    ::= { vehicleDetectorEntry 5 }

--5.3.2.6   Vehicle Detector Delay Parameter
vehicleDetectorDelay OBJECT-TYPE
    SYNTAX Integer32 (0..2550)
    UNITS "decisecond"
    MAX-ACCESS read-write
    STATUS current
    DESCRIPTION "<Definition> Detector Delay Parameter in tenth seconds
        (0-255.0 sec). The period a detector actuation (input recognition)
        shall be delayed when the phase is not Green. 
    <Object Identifier> 1.3.6.1.4.1.1206.4.2.1.2.2.1.6
    <Object Type> P"
    REFERENCE "NEMA TS 2 Clause 3.5.5.5.4.a"
    ::= { vehicleDetectorEntry 6 }

--5.3.2.7   Vehicle Detector Extend Parameter
vehicleDetectorExtend OBJECT-TYPE
    SYNTAX Integer32 (0..255)
    UNITS "decisecond"
    MAX-ACCESS read-write
    STATUS current
    DESCRIPTION "<Definition> Detector Extend Parameter in tenth seconds
        (0-25.5 sec). The period a vehicle detector actuation (input duration)
        shall be extended from the point of termination, when the phase is
        Green.
    <Object Identifier> 1.3.6.1.4.1.1206.4.2.1.2.2.1.7
    <Object Type> P"
    REFERENCE "NEMA TS 2 Clause 3.5.5.5.4.b"
    ::= { vehicleDetectorEntry 7 }

--5.3.2.8   Vehicle Detector Queue Limit
vehicleDetectorQueueLimit OBJECT-TYPE
    SYNTAX Integer32 (0..255)
    UNITS "second"
    MAX-ACCESS read-write
    STATUS current
    DESCRIPTION "<Definition> Detector Queue Limit parameter in seconds 
        (0-255 sec). The length of time that an actuation from a queue
        detector may continue into the phase green. This time begins when the
        phase becomes green and when it expires any associated detector inputs
        shall be ignored. This time may be shorter due to other overriding
        device parameters (i.e. Maximum time, Force Offs, ...).
    <Object Identifier> 1.3.6.1.4.1.1206.4.2.1.2.2.1.8
    <Object Type> P"
    ::= { vehicleDetectorEntry 8 }

--5.3.2.9   Vehicle Detector No Activity Parameter
vehicleDetectorNoActivity OBJECT-TYPE
    SYNTAX Integer32 (0..65535)
    UNITS "minute"
    MAX-ACCESS read-write
    STATUS current
    DESCRIPTION "<Definition> Detector No Activity diagnostic Parameter in
        minutes (1-65535 min.). If an active detector does not exhibit an
        actuation in the specified period, it is considered a fault by the
        diagnostics and the detector is classified as Failed. A value of zero for
        this object shall disable this diagnostic for this detector.
    <Object Identifier> 1.3.6.1.4.1.1206.4.2.1.2.2.1.9
    <Object Type> P"
    REFERENCE "NEMA TS 2 Clause 3.9.3.1.4.1"
    ::= { vehicleDetectorEntry 9 }

--5.3.2.10   Vehicle Detector Maximum Presence Parameter
vehicleDetectorMaxPresence OBJECT-TYPE
    SYNTAX Integer32 (0..255)
    UNITS "minute"
    MAX-ACCESS read-write
    STATUS current
    DESCRIPTION "<Definition> Detector Maximum Presence diagnostic Parameter
        in minutes (0-255 min.). If an active detector exhibits continuous
        detection for too long a period, it is considered a fault by the
        diagnostics and the detector is classified as Failed. A value of zero for
        this object shall disable this diagnostic for this detector.
    <Object Identifier> 1.3.6.1.4.1.1206.4.2.1.2.2.1.10
    <Object Type> P"
    REFERENCE "NEMA TS 2 Clause 3.9.3.1.4.2"
    ::= { vehicleDetectorEntry 10 }

--5.3.2.11  Vehicle Detector Erratic Counts Parameter
vehicleDetectorErraticCounts OBJECT-TYPE
    SYNTAX Integer32 (0..255)
    UNITS "count"
    MAX-ACCESS read-write
    STATUS current
    DESCRIPTION "<Definition> Detector Erratic Counts diagnostic Parameter in
        counts/minute (0-255 cpm). If an active detector exhibits excessive
        actuations, it is considered a fault by the diagnostics and the
        detector is classified as Failed. A value of zero for this object shall
        disable this diagnostic for this detector.
    <Object Identifier> 1.3.6.1.4.1.1206.4.2.1.2.2.1.11
    <Object Type> P"
    REFERENCE "NEMA TS 2 Clause 3.9.3.1.4.3"
    ::= { vehicleDetectorEntry 11 }

--5.3.2.12  Vehicle Detector Fail Time Parameter
vehicleDetectorFailTime OBJECT-TYPE
    SYNTAX Integer32 (0..255)
    UNITS "second"
    MAX-ACCESS read-write
    STATUS current
    DESCRIPTION "<Definition> Detector Fail Time in seconds (0..255 sec). If a
        detector diagnostic indicates that the associated detector input is
        failed, then a call shall be placed on the associated phase during all
        non-green intervals. When each green interval begins the call shall be
        maintained for the length of time specified by this object and then
        removed. If the value of this object equals the maximum value (255)
        then a constant call shall be placed on the associated phase (max
        recall). If the value of this object equals zero, then no call shall be
        placed on the associated phase for any interval (no recall). Compliant
        devices may support a limited capability for this object (i.e. only
        max recall). At a minimum, the max recall setting must be supported.
    <Object Identifier> 1.3.6.1.4.1.1206.4.2.1.2.2.1.12
    <Object Type> P"
    ::= { vehicleDetectorEntry 12 }

--5.3.2.13  Vehicle Detector Alarms
vehicleDetectorAlarms OBJECT-TYPE
    SYNTAX Integer32 (0..255)
    MAX-ACCESS read-only
    STATUS current
    DESCRIPTION "<Definition> This object shall return indications of detector
        alarms as identified by the CU. Detector Alarms are indicated as follows:

        Bit 7: Other Fault - The detector has failed due to some other cause.
        Bit 6: Reserved.
        Bit 5: Reserved.
        Bit 4: Configuration Fault - Detector is assigned but is not supported.
        Bit 3: Communications Fault - Communications to the device (if
                present) have failed.
        Bit 2: Erratic Output Fault - This detector has been flagged as
                non-operational due to erratic outputs (excessive counts) by
                the CU detector diagnostic.
        Bit 1: Max Presence Fault - This detector has been flagged as
                non-operational due to a presence indicator that exceeded the
                maximum expected time by the CU detector diagnostic.
        Bit 0: No Activity Fault - This detector has been flagged as
                non-operational due to lower than expected activity by the CU
                detector diagnostic.

        Once set a bit shall maintain its state as long as the condition
        exists. The bit shall clear when the condition no longer exists.

        The value of this object is the same for all vehicle detector sets.
    <Object Identifier> 1.3.6.1.4.1.1206.4.2.1.2.2.1.13
    <Object Type> S"
    ::= { vehicleDetectorEntry  13 }

--5.3.2.14  Vehicle Detector Reported Alarms
vehicleDetectorReportedAlarms OBJECT-TYPE
    SYNTAX Integer32 (0..255)
    MAX-ACCESS read-only
    STATUS current
    DESCRIPTION "<Definition> This object shall return detector device
        reported alarms communicated to the CU through an external device. 
        
        Detector Alarms are indicated as follows:
        Bit 7: Reserved.
        Bit 6: Reserved.
        Bit 5: Reserved.
        Bit 4: Excessive Change Fault - This detector has been flagged as
                non-operational due to an inductance change that exceeded
                expected values.
        Bit 3: Shorted Loop Fault - This detector has been flagged as
                non-operational due to a shorted loop wire.
        Bit 2: Open Loop Fault - This detector has been flagged as
                non-operational due to an open loop (broken wire).
        Bit 1: Watchdog Fault - This detector has been flagged as
                non-operational due to a watchdog error.
        Bit 0: Other - This detector has been flagged as non-operational due
                to some other error.

        Once set a bit shall maintain its state as long as the condition
        exists. The bit shall clear when the condition no longer exists.

        The value of this object is the same for all vehicle detector sets.
    <Object Identifier> 1.3.6.1.4.1.1206.4.2.1.2.2.1.14
    <Object Type> S"
    ::= { vehicleDetectorEntry  14 }

--5.3.2.15  Vehicle Detector Reset
vehicleDetectorReset OBJECT-TYPE
    SYNTAX Integer32 (0..1)
    MAX-ACCESS read-write
    STATUS current
    DESCRIPTION "<Definition> This object when set to TRUE (one) shall cause
        the CU to command the associated detector to reset. This object shall
        automatically return to FALSE (zero) after the CU has issued the reset
        command.

        Note: this may affect other detector (detector channels) that are
        physically attached to a common reset line.

        There is no object in the vehicleDetectorSetTable corresponding to
        vehicleDetectorReset.
    <Object Identifier> 1.3.6.1.4.1.1206.4.2.1.2.2.1.15
    <Object Type> C"
    ::= { vehicleDetectorEntry 15 }

--5.3.2.16  Vehicle Detector Options 2
vehicleDetectorOptions2 OBJECT-TYPE
    SYNTAX Integer32 (0..255)
    MAX-ACCESS read-write
    STATUS current
    DESCRIPTION "<Definition> A bit-mapped value as defined below for
        configuring detector options.
    <Format>
        Bit 7: Reserved 
        Bit 6: Reserved
        Bit 5: Reserved
        Bit 4: Reserved
        Bit 3	0=DISABLED, 1=ENABLED Connected Vehicle Detector: When enabled,
					this detector is assigned to a Connected Vehicle Detector as
					configured in the cvDetectorTable. Any CV Application
					Parameters, such as Red Light Violation Warning and Assured
					Green Period, apply if this detector is actuated.
        Bit 2    0=CUSTOM, 1=NTCIP  Default Detector Speed Mode Option. For a
                    vehicle detector operating in pairs, this option is used
                    when there is an error on one of the paired detectors. It
                    identifies how the controller should calculate speed
                    without the other detector. CUSTOM indicates a
                    manufacturer specific calculation. NTCIP indicates the use
                    of the calculation Speed = (Average Vehicle Length +
                    Detector Length) / Detect Time. 
        Bit 1    0=TRAIL, 1=LEAD  Detector Placement Option. For a vehicle
                    detector operating in pairs, this option indicates the
                    leading and trailing detectors. LEAD indicates that the
                    detector is the leading detector of the pair. TRAIL
                    indicates that the detector is a trailing detector in
                    the pair.
        Bit 0    0=DISABLED, 1=ENABLED  Enable Speed Data. If enabled, the
                    detector is used to collect speed data (See
                    volumeOccupancyTable and detectorAvgSpeed). This
                    capability may not be supported on all detector inputs to
                    a device.
    <Object Identifier> 1.3.6.1.4.1.1206.4.2.1.2.2.1.16
    <Object Type> P"
    ::= { vehicleDetectorEntry 16 }

--5.3.2.17  Vehicle Detector Paired Detector
vehicleDetectorPairedDetector OBJECT-TYPE
    SYNTAX Integer32 (0..255)
    MAX-ACCESS read-write
    STATUS current
    DESCRIPTION "<Definition> This is a detector identifier
        (vehicleDetectorNumber) that is used to determine speed. A value of zero
        indicates there is no paired detector. Setting this value will
        automatically add this detector as the given detector's
        vehicleDetectorPairedDetector.  This value shall not exceed maxVehicleDetectors. 

        The value of this object is the same for all vehicle detector sets.
    <Object Identifier> 1.3.6.1.4.1.1206.4.2.1.2.2.1.17
    <Object Type> P"
    DEFVAL { 0 }
    ::= { vehicleDetectorEntry 17 }

--5.3.2.18  Vehicle Detector Paired Detector Spacing
vehicleDetectorPairedDetectorSpacing OBJECT-TYPE
    SYNTAX Integer32 (0..65535)
    UNITS "centimeter"
    MAX-ACCESS read-write
    STATUS current
    DESCRIPTION "<Definition> This parameter allows the user to set the
        spacing, in centimeters between paired detectors for use in
        calculating vehicle speeds. This parameter is measured from the
        leading edge of one detector to the leading edge of the paired
        detector. A value of zero indicates there is no paired detector.

        The value of this object is the same for all vehicle detector sets.
    <Object Identifier> 1.3.6.1.4.1.1206.4.2.1.2.2.1.18
    <Object Type> P"
    DEFVAL { 0 }
    ::= { vehicleDetectorEntry 18 }

--5.3.2.19  Vehicle Detector Average Vehicle Length
vehicleDetectorAvgVehicleLength OBJECT-TYPE
    SYNTAX Integer32 (1..4000)
    UNITS "centimeter"
    MAX-ACCESS read-write
    STATUS current
    DESCRIPTION "<Definition> This parameter allows the user to set the
        average vehicle length for use in determining speed and
        classification. This allows for a range of lengths between 1 to
        4000 centimeters in length.
    <Object Identifier> 1.3.6.1.4.1.1206.4.2.1.2.2.1.19
    <Object Type> P"
    ::= { vehicleDetectorEntry 19 }

--5.3.2.20  Vehicle Detector Length Parameter
vehicleDetectorLength OBJECT-TYPE
    SYNTAX Integer32 (1..65535)
    UNITS "centimeter"
    MAX-ACCESS read-write
    STATUS current
    DESCRIPTION "<Definition> This parameter allows the user to set the length
        of the detection zone. In the case of a loop detector, this is the
        length of the loop.
        
        Values 01 to 4000 are used to represent the length.
        This allows for a range of lengths between 1 to 4000 centimeters in
        length. The value of 65535 shall be returned to represent no length
        set. Values 4001 to 65534 are not used.

        The value of this object is the same for all vehicle detector sets.
    <Object Identifier> 1.3.6.1.4.1.1206.4.2.1.2.2.1.20
    <Object Type> P"
    DEFVAL { 65535 }
    ::= { vehicleDetectorEntry 20 }

--5.3.2.21  Vehicle Detector Travel Mode
vehicleDetectorTravelMode OBJECT-TYPE
    SYNTAX INTEGER { other (1),
                     vehicle (2),
                     transit (3),
                     bicycle (4) }
    MAX-ACCESS read-write
    STATUS current
    DESCRIPTION "<Definition> This parameter allows the user to identify
        detectors for specific types of travel modes.
        other:   refers to a detector for a travel type not defined in this standard
        vehicle: refers to a detector identified for vehicles.
        transit: refers to a detector identified for transit vehicles.
        bicycle: refers to a detector identified for bicycles.
    <Object Identifier> 1.3.6.1.4.1.1206.4.2.1.2.2.1.21
    <Object Type> P"
    DEFVAL { 2 }
    ::= { vehicleDetectorEntry 21 }


--5.3.3 Maximum Vehicle Detector Groups
maxVehicleDetectorGroups OBJECT-TYPE
    SYNTAX Integer32 (1..32)
    UNITS "group"
    MAX-ACCESS read-only
    STATUS current
    DESCRIPTION "<Definition> The maximum number of detector groups
        (8 detectors per group) this device supports. This value is equal to
        TRUNCATE [(maxVehicleDetectors + 7 ) / 8]. This object indicates the
        maximum number of rows which shall appear in the
        vehicleDetectorStatusGroupTable and the vehicleDetectorControlGroupTable.

        This object was named maxVehicleDetectorStatusGroups in 1202 v03.
    <Object Identifier> 1.3.6.1.4.1.1206.4.2.1.2.3
    <Object Type> S"
    ::= { detector 3 }

--5.3.4 Vehicle Detector Status Group Table
vehicleDetectorStatusGroupTable OBJECT-TYPE
    SYNTAX SEQUENCE OF VehicleDetectorStatusGroupEntry
    MAX-ACCESS not-accessible
    STATUS current
    DESCRIPTION "<Definition> A table containing detector status in groups of
        eight detectors. The number of rows in this table is equal to the
        maxVehicleDetectorGroups object.
    <TableType> static
    <Object Identifier> 1.3.6.1.4.1.1206.4.2.1.2.4"
    ::= { detector 4 }

vehicleDetectorStatusGroupEntry OBJECT-TYPE
    SYNTAX VehicleDetectorStatusGroupEntry
    MAX-ACCESS not-accessible
    STATUS current
    DESCRIPTION "<Definition> A group (row) of detector status.
    <Object Identifier> 1.3.6.1.4.1.1206.4.2.1.2.4.1"
    INDEX  { vehicleDetectorStatusGroupNumber }
    ::= { vehicleDetectorStatusGroupTable  1 }

VehicleDetectorStatusGroupEntry ::= SEQUENCE {
    vehicleDetectorStatusGroupNumber    Integer32,
    vehicleDetectorStatusGroupActive    Integer32,
    vehicleDetectorStatusGroupAlarms    Integer32 }
 
--5.3.4.1   Vehicle Detector Status Group Number
vehicleDetectorStatusGroupNumber OBJECT-TYPE
    SYNTAX Integer32 (1..32)
    UNITS "group"
    MAX-ACCESS not-accessible
    STATUS current
    DESCRIPTION "<Definition> The detector status group number for objects in
        this row. This value shall not exceed the
        maxVehicleDetectorGroups object value.
    <Object Identifier> 1.3.6.1.4.1.1206.4.2.1.2.4.1.1"
    ::= { vehicleDetectorStatusGroupEntry 1 }

--5.3.4.2   Vehicle Detector Status Group Active
vehicleDetectorStatusGroupActive OBJECT-TYPE
    SYNTAX Integer32 (0..255)
    MAX-ACCESS read-only
    STATUS current
    DESCRIPTION "<Definition> This object shall return the detection STATUS of
        each detector associated with the group. Each detector shall be
        represented as ON (detect) or OFF (no-detect) by individual bits in
        this object. If a detector is ON then the associated bit shall be set
        (1). If a detector is OFF then the associated bit shall be clear (0).

        Bit 7: Det # = ( vehicleDetectorStatusGroupNumber * 8)
        Bit 6: Det # = ( vehicleDetectorStatusGroupNumber * 8) - 1
        Bit 5: Det # = ( vehicleDetectorStatusGroupNumber * 8) - 2
        Bit 4: Det # = ( vehicleDetectorStatusGroupNumber * 8) - 3
        Bit 3: Det # = ( vehicleDetectorStatusGroupNumber * 8) - 4
        Bit 2: Det # = ( vehicleDetectorStatusGroupNumber * 8) - 5
        Bit 1: Det # = ( vehicleDetectorStatusGroupNumber * 8) - 6
        Bit 0: Det # = ( vehicleDetectorStatusGroupNumber * 8) - 7
    <Object Identifier> 1.3.6.1.4.1.1206.4.2.1.2.4.1.2
    <Object Type> S"
    ::= { vehicleDetectorStatusGroupEntry 2 }

--5.3.4.3   Vehicle Detector Alarm Group Status
vehicleDetectorStatusGroupAlarms OBJECT-TYPE
    SYNTAX Integer32 (0..255)
    MAX-ACCESS read-only
    STATUS current
    DESCRIPTION "<Definition> This object shall return the alarm status of the
        detectors associated with the group. Each detector alarm status shall
        be represented as ON or OFF by individual bits in this object. If any
        detector alarm (defined in the vehicleDetectorAlarm object) is active
        the associated bit shall be set (1). If a detector alarm is not active
        the associated bit shall be clear (0).

        Bit 7: Det # = ( vehicleDetectorStatusGroupNumber * 8)
        Bit 6: Det # = ( vehicleDetectorStatusGroupNumber * 8) - 1
        Bit 5: Det # = ( vehicleDetectorStatusGroupNumber * 8) - 2
        Bit 4: Det # = ( vehicleDetectorStatusGroupNumber * 8) - 3
        Bit 3: Det # = ( vehicleDetectorStatusGroupNumber * 8) - 4
        Bit 2: Det # = ( vehicleDetectorStatusGroupNumber * 8) - 5
        Bit 1: Det # = ( vehicleDetectorStatusGroupNumber * 8) - 6
        Bit 0: Det # = ( vehicleDetectorStatusGroupNumber * 8) - 7
    <Object Identifier> 1.3.6.1.4.1.1206.4.2.1.2.4.1.3
    <Object Type> S"
    ::= { vehicleDetectorStatusGroupEntry 3 }

--5.3.5 Vehicle Detector Data
volumeOccupancyReport   OBJECT IDENTIFIER 
    ::= { detector 5 }

-- This node contains the objects necessary to support volume / occupancy reporting.

--5.3.5.1   Volume / Occupancy Sequence
volumeOccupancySequence OBJECT-TYPE
    SYNTAX Integer32 (0..255)
    UNITS "sequence"
    MAX-ACCESS read-only
    STATUS current
    DESCRIPTION "<Definition> This object defines a sequence number for
        Volume/Occupancy data collection. This object is used to detect
        duplicate or missing reports. The value cycles within the limits of 0
        to 255. This object is incremented by one at the expiration of the
        volumeOccupancyPeriod time.
    <Object Identifier> 1.3.6.1.4.1.1206.4.2.1.2.5.1
    <Object Type> S"
    ::= { volumeOccupancyReport 1 }

--5.3.5.2   Volume / Occupancy Period
volumeOccupancyPeriod OBJECT-TYPE
    SYNTAX Integer32 (0..65535)
    UNITS "second"
    MAX-ACCESS read-write
    STATUS current
    DESCRIPTION "This object indicates the number of seconds
        (0-3600 seconds) that comprise the Volume/Occupancy/Speed collection
        period. When the collection period expires the device shall increment
        the volumeOccupancySequence, update the volumeOccupancyTable entries
        and reset the volume occupancy timer. 

        A value of zero indicates no sampling is performed. 

        A value of 65535 indicates that the sample period is equal to the current
        cycle length recorded at local zero. If the sample period is
        configured to use the cycle length but the ASC is running in Free
        mode, then no data collection is performed.

        Value       Indication
        0           No sampling is performed
        1-3600      Volume/Occupancy/Speed period in seconds
        3601-65534  Reserved
        65535       Sample period is same as cycle period recorded at local zero.
    <Object Identifier> 1.3.6.1.4.1.1206.4.2.1.2.5.2
    <Object Type> P"
    ::= { volumeOccupancyReport 2 }

--5.3.5.3   Active Volume / Occupancy Detectors
activeVolumeOccupancyDetectors OBJECT-TYPE
    SYNTAX Integer32 (0..255)
    UNITS "detector"
    MAX-ACCESS read-only
    STATUS deprecated
    DESCRIPTION "<Definition> The number of detectors in this device. This
        object indicates how many rows are in the volumeOccupancyTable object.
        There shall be a row for every detector that is collecting volume,
        occupancy, or speed data (refer to detectorOptions in the
        detectorTable).
    <Object Identifier> 1.3.6.1.4.1.1206.4.2.1.2.5.3
    <Object Type> S"
    ::= { volumeOccupancyReport 3 }

--5.3.5.3   Volume / Occupancy Table
volumeOccupancyTable OBJECT-TYPE
    SYNTAX SEQUENCE OF VolumeOccupancyEntry
    MAX-ACCESS not-accessible
    STATUS current
    DESCRIPTION "<Definition> A table containing Detector Volume, Occupancy
        and Speed data collected from vehicle detectors. The number of rows
		in this table is equal to the maxVehicleDetectors object.
    <TableType> static
    <Object Identifier> 1.3.6.1.4.1.1206.4.2.1.2.5.4"
    ::= { volumeOccupancyReport 4 }

volumeOccupancyEntry OBJECT-TYPE
    SYNTAX VolumeOccupancyEntry
    MAX-ACCESS not-accessible
    STATUS current
    DESCRIPTION "<Definition> The Volume, Occupancy and Speed data collected
        for one of the detectors in the device.
    <Object Identifier> 1.3.6.1.4.1.1206.4.2.1.2.5.4.1"
    INDEX   { vehicleDetectorNumber }
    ::= { volumeOccupancyTable 1 }

VolumeOccupancyEntry ::= SEQUENCE { 
    detectorVolume      Integer32,
    detectorOccupancy   Integer32,
    detectorAvgSpeed    Integer32 }
 
--5.3.5.3.1 Volume Data
detectorVolume OBJECT-TYPE
    SYNTAX Integer32 (0..65535)
    UNITS "vehicle"
    MAX-ACCESS read-only
    STATUS current
    DESCRIPTION "<Definition> Detector Volume data collected over the
        volumeOccupancyPeriod. This value shall range from 0 to 65534 indicating the volume of traffic crossing the associated vehicleDetectorNumber during the collection period. The value 65535 shall indicate volume overflow.
    <Object Identifier> 1.3.6.1.4.1.1206.4.2.1.2.5.4.1.1
    <Object Type> S"
    ::= { volumeOccupancyEntry 1 }

--5.3.5.3.2 Occupancy Data
detectorOccupancy OBJECT-TYPE
    SYNTAX Integer32 (0..255)
    UNITS "percent"
    MAX-ACCESS read-only
    STATUS current
    DESCRIPTION "<Definition> Detector Occupancy as a percentage of the
        volumeOccupancyPeriod over which the data was collected or Detector
        Unit Diagnostic Information. The value of the object shall indicate
        occupancy or detector diagnostic information as follows:

        Range   Meaning
        0-200   Detector Occupancy in 0.5% Increments
        201-209 Reserved
        210     Max Presence Fault
        211     No Activity Fault
        212     Open loop Fault
        213     Shorted loop Fault
        214     Excessive Change Fault
        215     Reserved
        216     Watchdog Fault
        217     Erratic Output Fault
        218-255 Reserved 

        Faults shall be indicated for all collection periods during which a
        fault is detected if either occupancy data or volume data is being
        collected. The highest numbered fault shall be presented if more than
        one fault is active (i.e. indicate OpenLoop rather than NoActivity).
    <Object Identifier> 1.3.6.1.4.1.1206.4.2.1.2.5.4.1.2
    <Object Type> S"
    ::= { volumeOccupancyEntry 2 }

--5.3.5.3.3 Speed Data
detectorAvgSpeed OBJECT-TYPE
    SYNTAX Integer32 (0..511)
    UNITS "0.5 kilometers/hour"
    MAX-ACCESS read-only
    STATUS current
    DESCRIPTION  "<Definition>Average vehicle speed during the
        volumeOccupancyPeriod over which the data was collected. The value of
        the object shall indicate average vehicle speed as follows:

        Range Meaning
        0-508 Average vehicle speed in 0.5 kilometers per hour
        509   Reserved
        510   Average vehicle speed is 255 kilometers per hour or higher
        511   Invalid or missing value
    <Object Identifier> 1.3.6.1.4.1.1206.4.2.1.2.5.4.1.3
    <Object Type> S"
    DEFVAL { 511 }
    ::= { volumeOccupancyEntry 3 }

--5.3.5.5   Volume / Occupancy Period - Version 3
volumeOccupancyPeriodV3 OBJECT-TYPE
    SYNTAX Integer32 (0..65535)
    UNITS "second"
    MAX-ACCESS read-write
    STATUS deprecated
    DESCRIPTION "<Definition> This object indicates the number of seconds
        (0-3600 seconds) that comprise the Volume/Occupancy/Speed collection
        period. When the collection period expires the device shall increment
        the volumeOccupancySequence, update the volumeOccupancyTable entries
        and reset the volume occupancy timer. If the value is 0, the value in
        volumeOccupancyPeriod is used if indicated (has a valid non-zero
        value). If both the volumeOccupancyPeriod and volumeOccupancyPeriodV3
        are 0, then no sampling is to be performed. If both the
        volumeOccupancyPeriod and volumeOccupancyPeriodV3 are non-zero then
        the volumeOccupancyPeriod takes precedence.

        A value of 65535 indicates that the sample period equal to current
        cycle length recorded at local zero. If the sample period is
        configured to use the cycle length but the ASC is running in Free
        mode, then no data collection is performed.

        Value       Indication
        0           Value of volumeOccupancyPeriod is used if indicated
        1-3600      Volume/Occupancy/Speed period in seconds
        3601-65534  Reserved
        65535       Sample period is same as cycle period recorded at local
                        zero.
    <Object Identifier> 1.3.6.1.4.1.1206.4.2.1.2.5.5
    <Object Type> P"
    ::= { volumeOccupancyReport 5 }

--5.3.5.4   Volume / Occupancy Sample Time
detectorSampleTime OBJECT-TYPE
    SYNTAX Counter32
    UNITS "second"
    MAX-ACCESS read-only
    STATUS current
    DESCRIPTION "The local time, expressed in seconds since 00:00:00
        (midnight) January 1, 1970 of the same time offset, representing the
        end time of the last completed vehicle detector data collection
        period. This value changes by 3600 seconds in response to a DST event.
    <Object Identifier> 1.3.6.1.4.1.1206.4.2.1.2.5.6
    <Object Type> S"
    ::= { volumeOccupancyReport 6 }

--5.3.5.5   Volume / Occupancy Sample Duration
detectorSampleDuration OBJECT-TYPE
    SYNTAX Integer32 (0..3600)
    UNITS "second"
    MAX-ACCESS read-only
    STATUS current
    DESCRIPTION "<Definition> This object indicates the number of seconds
        (1-3600 seconds) that comprise the duration of the pedestrian detector
        data collection period. A value of zero indicates that duration is
        invalid.  
    <Object Identifier> 1.3.6.1.4.1.1206.4.2.1.2.5.7
    <Object Type> S"
    ::= { volumeOccupancyReport 7 }

--5.3.6 Maximum Pedestrian Detectors
maxPedestrianDetectors OBJECT-TYPE
    SYNTAX Integer32 (1..255)
    UNITS "detector"
    MAX-ACCESS read-only
    STATUS current
    DESCRIPTION "<Definition> The Maximum Number of Pedestrian Detectors this
        Controller Unit supports. This object indicates the maximum rows which
        shall appear in the pedestrianDetectorTable object.
    <Object Identifier> 1.3.6.1.4.1.1206.4.2.1.2.6
    <Object Type> S"
    ::= { detector 6 }

--5.3.7 Pedestrian Detector Parameter Table
pedestrianDetectorTable OBJECT-TYPE
    SYNTAX SEQUENCE OF PedestrianDetectorEntry
    MAX-ACCESS not-accessible
    STATUS current
    DESCRIPTION "<Definition> A table containing Controller Unit pedestrian
        detector parameters. The number of rows in this table is equal to the
        maxPedestrianDetectors object.

        The objects in this table correspond to the matching objects in the
        first set (pedestrianDetectorSetNumber = 1) of the pedestrianDetectorSetTable.

    <TableType> static
    <Object Identifier> 1.3.6.1.4.1.1206.4.2.1.2.7"
    ::= { detector 7 }

pedestrianDetectorEntry OBJECT-TYPE
    SYNTAX PedestrianDetectorEntry
    MAX-ACCESS not-accessible
    STATUS current
    DESCRIPTION "<Definition> Parameters for a specific Controller Unit
        pedestrian detector.
    <Object Identifier> 1.3.6.1.4.1.1206.4.2.1.2.7.1"
    INDEX   { pedestrianDetectorNumber }
    ::= { pedestrianDetectorTable 1 }

PedestrianDetectorEntry ::= SEQUENCE {
    pedestrianDetectorNumber        Integer32,
    pedestrianDetectorCallPhase     Integer32,
    pedestrianDetectorNoActivity    Integer32,
    pedestrianDetectorMaxPresence   Integer32,
    pedestrianDetectorErraticCounts Integer32,
    pedestrianDetectorAlarms        Integer32,
    pedestrianDetectorReset         Integer32,
    pedestrianButtonPushTime        Integer32,
    pedestrianDetectorOptions       Integer32,
    pedestrianDetectorDescription   SnmpAdminString }
 
--5.3.7.1   Pedestrian Detector Number
pedestrianDetectorNumber OBJECT-TYPE
    SYNTAX Integer32 (1..255)
    UNITS "detector"
    MAX-ACCESS not-accessible
    STATUS current
    DESCRIPTION "<Definition> The pedestrianDetector number for objects in
        this row. The value shall not exceed the maxPedestrianDetectors object
        value.
    <Object Identifier> 1.3.6.1.4.1.1206.4.2.1.2.7.1.1"
    ::= { pedestrianDetectorEntry 1 }

--5.3.7.2   Pedestrian Detector Call Phase Parameter
pedestrianDetectorCallPhase OBJECT-TYPE
    SYNTAX Integer32 (0..255)
    UNITS "phase"
    MAX-ACCESS read-write
    STATUS current
    DESCRIPTION "<Definition> This object contains assigned phase number for
        the pedestrian detector input associated with this row. The associated
        detector call capability is enabled when this object is set to a
        non-zero value. The value shall not exceed the value of maxPhases. A value of zero indicates no call phase.
    <Object Identifier> 1.3.6.1.4.1.1206.4.2.1.2.7.1.2
    <Object Type> P"
    ::= { pedestrianDetectorEntry 2 }

--5.3.7.3   Pedestrian Detector No Activity Parameter
pedestrianDetectorNoActivity OBJECT-TYPE
    SYNTAX Integer32 (0..65535)
    UNITS "minute"
    MAX-ACCESS read-write
    STATUS current
    DESCRIPTION "<Definition> Pedestrian Detector No Activity diagnostic
        Parameter in minutes (1-65535 min.). If an active detector does not
        exhibit an actuation in the specified period, it is considered a fault
        by the diagnostics and the detector is classified as Failed. A value
        of 0 for this object shall disable this diagnostic for this detector.
    <Object Identifier> 1.3.6.1.4.1.1206.4.2.1.2.7.1.3
    <Object Type> P"
    REFERENCE "NEMA TS 2 Clause 3.9.3.1.4.1"
    ::= { pedestrianDetectorEntry 3 }

--5.3.7.4   Pedestrian Detector Maximum Presence Parameter
pedestrianDetectorMaxPresence OBJECT-TYPE
    SYNTAX Integer32 (0..255)
    UNITS "minute"
    MAX-ACCESS read-write
    STATUS current
    DESCRIPTION "<Definition> Pedestrian Detector Maximum Presence diagnostic
        Parameter in minutes (0-255 min.). If an active detector exhibits
        continuous detection for too long a period, it is considered a fault
        by the diagnostics and the detector is classified as Failed. A value
        of 0 for this object shall disable this diagnostic for this detector.
    <Object Identifier> 1.3.6.1.4.1.1206.4.2.1.2.7.1.4
    <Object Type> P"
    REFERENCE "NEMA TS 2 Clause 3.9.3.1.4.2"
    ::= { pedestrianDetectorEntry 4 }

--5.3.7.5   Pedestrian Detector Erratic Counts Parameter
pedestrianDetectorErraticCounts OBJECT-TYPE
    SYNTAX Integer32 (0..255)
    UNITS "count"
    MAX-ACCESS read-write
    STATUS current
    DESCRIPTION "<Definition> Pedestrian Detector Erratic Counts diagnostic
        Parameter in counts/minute (0-255 cpm). If an active detector exhibits
        excessive actuations, it is considered a fault by the diagnostics and
        the detector is classified as Failed. A value of zero for this object
        shall disable this diagnostic for this detector.
    <Object Identifier> 1.3.6.1.4.1.1206.4.2.1.2.7.1.5
    <Object Type> P"
    REFERENCE "NEMA TS 2 Clause 3.9.3.1.4.3"
    ::= { pedestrianDetectorEntry 5 }

--5.3.7.6   Pedestrian Detector Alarms
pedestrianDetectorAlarms OBJECT-TYPE
    SYNTAX Integer32 (0..255)
    MAX-ACCESS read-only
    STATUS current
    DESCRIPTION "<Definition> This object shall return indications of pedestrian detector
        alarms identified by the CU. Detector Alarms are indicated as follows (0 = False, 1 = True):

        Bit 7: Other Fault - The detector has failed due to some other cause.
        Bit 6: Reserved.
        Bit 5: Reserved.
        Bit 4: Configuration Fault - Detector is assigned but is not supported.
        Bit 3: Communications Fault - Communications to the device (if present) have failed.
        Bit 2: Erratic Output Fault - This detector has been flagged as
                non-operational due to erratic outputs (excessive counts) by
                the CU detector diagnostic.
        Bit 1: Max Presence Fault - This detector has been flagged as
                non-operational due to a presence indicator that exceeded the
                maximum expected time by the CU detector diagnostic.
        Bit 0: No Activity Fault - This detector has been flagged as
                non-operational due to lower than expected activity by the CU
                detector diagnostic

        Once set a bit shall maintain its state as long as the condition
        exists. The bit shall clear when the condition no longer exists.
    <Object Identifier> 1.3.6.1.4.1.1206.4.2.1.2.7.1.6
    <Object Type> S"
    ::= { pedestrianDetectorEntry  6 }

--5.3.7.7   Pedestrian Detector Reset
pedestrianDetectorReset OBJECT-TYPE
    SYNTAX Integer32 (0..1)
    MAX-ACCESS read-write
    STATUS current
    DESCRIPTION "<Definition> This object when set to TRUE (one) shall cause
        the CU to command the associated detector to reset. This object shall
        automatically return to FALSE (zero) after the CU has issued the reset
        command.

        Note: this may affect other detector (detector channels) that are
        physically attached to a common reset line.
    <Object Identifier> 1.3.6.1.4.1.1206.4.2.1.2.7.1.7
    <Object Type> C"
    DEFVAL { 0 }
    ::= { pedestrianDetectorEntry 7 }

--5.3.7.8   Pedestrian Push Button Duration Parameter
pedestrianButtonPushTime OBJECT-TYPE
    SYNTAX Integer32 (0..255)
    UNITS "decisecond"
    MAX-ACCESS read-write
    STATUS current
    DESCRIPTION "<Definition> The minimum amount of time, in tenths of a
        second, a pedestrian call button is pressed to actuate additional
        accessible features such as increased pedestrian crossing times
        (phasePedAlternateWalk) or pedestrian clearance times
        (phasePedAlternateClearance). A value of zero indicates that all
        accessible pedestrian signal (APS) features are disabled for the
        associated detector.
        This value is the same for all pedestrian detector sets. 
        NOTE the pedestrian detector must be configured to allow Alternate timing. pedestrianDetectorOptions or pedestrianSetDetectorOptions.

        This value is the same for all pedestrian detector sets.  
    <Object Identifier> 1.3.6.1.4.1.1206.4.2.1.2.7.1.8
    <Object Type> P"
    DEFVAL { 0 }
    ::= { pedestrianDetectorEntry 8 }

--5.3.7.9   Pedestrian Detector Options
pedestrianDetectorOptions OBJECT-TYPE
    SYNTAX Integer32 (0..255)
    MAX-ACCESS read-write
    STATUS current
    DESCRIPTION " <Definition> Pedestrian Detector Options Parameter as
        follows (0=Disabled, 1=Enabled):

        Bit 7: Reserved.
        Bit 6: Reserved.
        Bit 5: Reserved.
        Bit 4: Advanced Walk: If enabled, the detector will place calls for the phase's pedestrian WALK indication to start before the phase's vehicle GREEN indication. 
        Bit 3: Delayed Walk: If enabled, the detector will place calls for the phase's pedestrian WALK indication to start after the phase's vehicle GREEN indication. 
        Bit 2: Non-locking: If enabled, detector will place non-locked calls instead  of locked calls.
        Bit 1: Alternate timing: If enabled, the detector will place calls for alternate ped timing instead of normal ped timing.
        Bit 0: Presence: If enabled, the detector indicates presence of
                pedestrians in the crosswalk instead of placing calls for
                service.
        
        A SET of both bits 3 & 4 shall result in bit 3=0 and bit 4=1. A SET of a 'reserved' bit to a value other than zero (0) shall return a badValue(3) error.
    <Object Identifier> 1.3.6.1.4.1.1206.4.2.1.2.7.1.9
    <Object Type> P"
    DEFVAL { 0 }
    ::= { pedestrianDetectorEntry 9 }

--5.3.7.10   Pedestrian Detector Description
pedestrianDetectorDescription OBJECT-TYPE
    SYNTAX SnmpAdminString 
    MAX-ACCESS read-write
    STATUS current
    DESCRIPTION "<Definition> A textual string indicate a user description for the vehicle detector (e.g. location). This value is the same for all pedestrian detector sets. 
    <Object Identifier> 1.3.6.1.4.1.1206.4.2.1.2.7.1.10
    <Object Type> P"
    ::= { pedestrianDetectorEntry 10 }

--5.3.8 Maximum Pedestrian Detector Groups
maxPedestrianDetectorGroups OBJECT-TYPE
    SYNTAX Integer32 (1..32)
    UNITS "group"
    MAX-ACCESS read-only
    STATUS current
    DESCRIPTION "<Definition>The maximum number of pedestrian detector status
        groups (8 detectors per group) this device supports. This value is
        equal to TRUNCATE [(maxPedestrianDetectors + 7 ) / 8]. This object
        indicates the maximum number of rows which shall appear in the
        pedestrianDetectorStatusGroupTable object.
    <Object Identifier> 1.3.6.1.4.1.1206.4.2.1.2.8
    <Object Type> S"
    ::= { detector 8 }

--5.3.9 Pedestrian Detector Status Group Table
pedestrianDetectorStatusGroupTable OBJECT-TYPE
    SYNTAX SEQUENCE OF PedestrianDetectorStatusGroupEntry
    MAX-ACCESS not-accessible
    STATUS current
    DESCRIPTION "<Definition> A table containing pedestrian detector status in
        groups of eight detectors. The number of rows in this table is equal
        to the maxPedestrianDetectorGroups object.
    <TableType> static
    <Object Identifier> 1.3.6.1.4.1.1206.4.2.1.2.9"
    ::= { detector 9 }

pedestrianDetectorStatusGroupEntry OBJECT-TYPE
    SYNTAX PedestrianDetectorStatusGroupEntry
    MAX-ACCESS not-accessible
    STATUS current
    DESCRIPTION "<Definition> A group (row) of pedestrian detector status.
    <Object Identifier> 1.3.6.1.4.1.1206.4.2.1.2.9.1"
    INDEX { pedestrianDetectorStatusGroupNumber }
    ::= { pedestrianDetectorStatusGroupTable 1 }

PedestrianDetectorStatusGroupEntry ::= SEQUENCE {
    pedestrianDetectorStatusGroupNumber Integer32,
    pedestrianDetectorStatusGroupActive Integer32,
    pedestrianDetectorStatusGroupAlarms Integer32 }

--5.3.9.1   Pedestrian Detector Status Group Number
pedestrianDetectorStatusGroupNumber OBJECT-TYPE
    SYNTAX Integer32 (1..32)
    UNITS "group"
    MAX-ACCESS not-accessible
    STATUS current
    DESCRIPTION "<Definition> The pedestrian detector status group number for
        objects in this row. This value shall not exceed the
        maxPedestrianDetectorGroups object value.
    <Object Identifier> 1.3.6.1.4.1.1206.4.2.1.2.9.1.1"
    ::= { pedestrianDetectorStatusGroupEntry 1 }

--5.3.9.2   Pedestrian Detector Status Group Active
pedestrianDetectorStatusGroupActive OBJECT-TYPE
    SYNTAX Integer32 (0..255)
    MAX-ACCESS read-only
    STATUS current
    DESCRIPTION "<Definition>This object shall return the detection status of
        each pedestrian detector associated with the group. Each detector
        shall be represented as ON (detect) or OFF (no-detect) by individual
        bits in this object. If a detector is ON then the associated bit shall
        be set (1). If a detector is OFF then the associated bit shall be
        clear (0).

        Bit 7: Det # = ( pedestrianDetectorStatusGroupNumber * 8)
        Bit 6: Det # = ( pedestrianDetectorStatusGroupNumber * 8) - 1
        Bit 5: Det # = ( pedestrianDetectorStatusGroupNumber * 8) - 2
        Bit 4: Det # = ( pedestrianDetectorStatusGroupNumber * 8) - 3
        Bit 3: Det # = ( pedestrianDetectorStatusGroupNumber * 8) - 4
        Bit 2: Det # = ( pedestrianDetectorStatusGroupNumber * 8) - 5
        Bit 1: Det # = ( pedestrianDetectorStatusGroupNumber * 8) - 6
        Bit 0: Det # = ( pedestrianDetectorStatusGroupNumber * 8) - 7
    <Object Identifier> 1.3.6.1.4.1.1206.4.2.1.2.9.1.2
    <Object Type> S"
    ::= { pedestrianDetectorStatusGroupEntry 2 }

--5.3.9.3   Pedestrian Detector Alarm Status
pedestrianDetectorStatusGroupAlarms OBJECT-TYPE
    SYNTAX Integer32 (0..255)
    MAX-ACCESS read-only
    STATUS current
    DESCRIPTION "<Definition> This object shall return the alarm status of the
        pedestrian detectors associated with the group. Each pedestrian
        detector alarm status shall be represented as ON or OFF by individual
        bits in this object. If any pedestrian detector alarm (defined in the
        pedestrianDetectorAlarms object) is active the associated bit shall be
        set (1). If a pedestrian detector alarm is not active the associated
        bit shall be clear (0).

        Bit 7: Det # = ( pedestrianDetectorStatusGroupNumber * 8)
        Bit 6: Det # = ( pedestrianDetectorStatusGroupNumber * 8) - 1
        Bit 5: Det # = ( pedestrianDetectorStatusGroupNumber * 8) - 2
        Bit 4: Det # = ( pedestrianDetectorStatusGroupNumber * 8) - 3
        Bit 3: Det # = ( pedestrianDetectorStatusGroupNumber * 8) - 4
        Bit 2: Det # = ( pedestrianDetectorStatusGroupNumber * 8) - 5
        Bit 1: Det # = ( pedestrianDetectorStatusGroupNumber * 8) - 6
        Bit 0: Det # = ( pedestrianDetectorStatusGroupNumber * 8) - 7
    <Object Identifier> 1.3.6.1.4.1.1206.4.2.1.2.9.1.3
    <Object Type> S"
    ::= { pedestrianDetectorStatusGroupEntry 3 }

--5.3.10    Pedestrian Detector Report
pedestrianDetectorReport OBJECT IDENTIFIER
    ::= { detector 10 }

-- This node contains the objects necessary to support pedestrian detector reporting.

--5.3.10.1  Pedestrian Sample Sequence
pedestrianDetectorSequence OBJECT-TYPE
    SYNTAX Integer32 (0..255)
    UNITS "sequence"
    MAX-ACCESS read-only
    STATUS current
    DESCRIPTION "<Definition> This object defines a Sequence Number for the
        pedestrian detector data collection. This object is used to detect
        duplicate or missing reports. The value cycles within the limits of
        0 to 255. This object is incremented by one at the expiration of the
        pedestrianDetectorPeriod time.
    <Object Identifier> 1.3.6.1.4.1.1206.4.2.1.2.10.1
    <Object Type> S"
    ::= { pedestrianDetectorReport 1 }

--5.3.10.2  Pedestrian Sample Period
pedestrianDetectorPeriod OBJECT-TYPE
    SYNTAX Integer32 (0..65535)
    UNITS "second"
    MAX-ACCESS read-write
    STATUS current
    DESCRIPTION "<Definition> This object defines the number of seconds
        (1-3600 seconds) that comprise the pedestrian detector data
        collection period. When the collection period expires the device shall
        increment the pedestrianDetectorSequence, update the
        pedestrianSampleTable entries, and reset the pedestrian volume timer. A
        value of 0 indicates that no sampling is to be performed.

        A value of 65534 indicates that the pedestrian detector data
        collection period is equal to vehicle sample period in effect.

        A value of 65535 indicates that the sample period equal to current
        cycle length recorded at local zero. If the sample period is
        configured to use the cycle length but the ASC is running in Free
        mode, then no data collection is performed.

        Value       Indication
        0           No pedestrian data collection is performed
        1-3600      Pedestrian data collection period in seconds
        3601-65533  Reserved
        65534       Pedestrian data collection period is equal to the vehicle
                        sample period in effect
        65535       Pedestrian data collection period is same as cycle period
                        recorded at local zero
    <Object Identifier> 1.3.6.1.4.1.1206.4.2.1.2.10.2
    <Object Type> P"
    ::= { pedestrianDetectorReport 2 }

--5.3.10.3  Active Pedestrian Sample Detectors
activePedestrianDetectors OBJECT-TYPE
    SYNTAX Integer32 (0..255)
    UNITS "detector"
    MAX-ACCESS read-only
    STATUS deprecated
    DESCRIPTION "<Definition> The number of detectors in this device. This
        object indicates how many rows are in the pedestrianSampleTable
        object. There shall be a row for every pedestrian detector that is
        collecting pedestrian data.
    <Object Identifier> 1.3.6.1.4.1.1206.4.2.1.2.10.3
    <Object Type> S"
    ::= { pedestrianDetectorReport 3 }

--5.3.10.3  Pedestrian Sample Table
pedestrianSampleTable OBJECT-TYPE
    SYNTAX SEQUENCE OF PedestrianSampleEntry
    MAX-ACCESS not-accessible
    STATUS current
    DESCRIPTION "<Definition> A table containing pedestrian data collected.
        The number of rows in this table is equal to the
        maxPedestrianDetectors object.
    <TableType> static
    <Object Identifier> 1.3.6.1.4.1.1206.4.2.1.2.10.4"
    ::= { pedestrianDetectorReport 4 }

pedestrianSampleEntry OBJECT-TYPE
    SYNTAX PedestrianSampleEntry
    MAX-ACCESS not-accessible
    STATUS current
    DESCRIPTION "<Definition> The data collected for one of the detectors in
        the device as part of a pedestrian detector data collection.
    <Object Identifier> 1.3.6.1.4.1.1206.4.2.1.2.10.4.1"
    INDEX { pedestrianDetectorNumber }
    ::= { pedestrianSampleTable 1 }

PedestrianSampleEntry ::= SEQUENCE {
    pedestrianDetectorVolume     Integer32,
    pedestrianDetectorActuations Integer32,
    pedestrianDetectorServices   Integer32 }

--5.3.10.3.1    Pedestrian Sample Volume
pedestrianDetectorVolume OBJECT-TYPE
    SYNTAX Integer32 (0..255)
    UNITS "pedestrian"
    MAX-ACCESS read-only
    STATUS current
    DESCRIPTION "<Definition>Pedestrian detector data collected over the data
        collection period. This value shall range from 0 to 254 indicating the
        volume of pedestrians crossing the associated pedestrian detector zone
        during the data collection period. The value 255 shall indicate volume
        overflow.
    <Object Identifier> 1.3.6.1.4.1.1206.4.2.1.2.10.4.1.1
    <Object Type> S"
    ::= { pedestrianSampleEntry 1 }

--5.3.10.3.2    Pedestrian Sample Actuations
pedestrianDetectorActuations OBJECT-TYPE
    SYNTAX Integer32 (0..255)
    UNITS "actuations"
    MAX-ACCESS read-only
    STATUS current
    DESCRIPTION "<Definition>Pedestrian actuations collected over the data
        collection period. The value of the object shall indicate pedestrian
        actuations or pedestrian detector diagnostic information as follows:

        Value   Indication
        0-200   Number of actuations
        201     Number of actuations exceeds 200.
        202-208 Reserved
        209     Other Fault
        210     Max Presence Fault
        211     No Activity Fault
        212     Reserved 
        213     Reserved 
        214     Reserved 
        215     Configuration Fault
        216     Communications Fault
        217     Erratic Output Fault
        218-255 Reserved

        Faults shall be indicated for all collection periods during which a
        fault is detected if either pedestrian volume or pedestrian actuations
        is being collected. The highest numbered fault shall be presented if
        more than one fault is active (i.e. indicate OpenLoop rather than
        NoActivity).
    <Object Identifier> 1.3.6.1.4.1.1206.4.2.1.2.10.4.1.2
    <Object Type> S"
    ::= { pedestrianSampleEntry 2 }

--5.3.10.3.3    Pedestrian Sample Services
pedestrianDetectorServices OBJECT-TYPE
    SYNTAX Integer32 (0..255)
    UNITS "service"
    MAX-ACCESS read-only
    STATUS current
    DESCRIPTION "<Definition> The number of pedestrian services (number of
        times the ped transitioned from don't walk to walk) collected over the
        data collection period. This value shall range from 0-254. A value of
        255 indicates an overflow condition.
    <Object Identifier> 1.3.6.1.4.1.1206.4.2.1.2.10.4.1.3
    <Object Type> S"
    ::= { pedestrianSampleEntry 3 }

--5.3.10.4  Pedestrian Volume / Actuation Sample Time
pedestrianDetectorSampleTime OBJECT-TYPE
    SYNTAX Counter32
    UNITS "second"
    MAX-ACCESS read-only
    STATUS current
    DESCRIPTION "The local time expressed in seconds since 00:00:00 (midnight)
        January 1, 1970 of the same time offset, representing the end time of
        the last completed pedestrian detector data collection period. This
        value changes by 3600 seconds in response to a DST event.
    <Object Identifier> 1.3.6.1.4.1.1206.4.2.1.2.10.5
    <Object Type> S"
    ::= { pedestrianDetectorReport 5 }

--5.3.10.5  Pedestrian Volume / Actuation Sample Duration
pedestrianDetectorSampleDuration OBJECT-TYPE
    SYNTAX Integer32 (0..3600)
    UNITS "second"
    MAX-ACCESS read-only
    STATUS current
    DESCRIPTION "<Definition> This object indicates the number of seconds
        (1-3600 seconds) that comprise the sampling of the pedestrian detector
        data collection period. A value of zero indicates that duration is
        invalid. 
    <Object Identifier> 1.3.6.1.4.1.1206.4.2.1.2.10.6
    <Object Type> S"
    ::= { pedestrianDetectorReport 6 }

--5.3.11    Maximum Vehicle Detector Control Groups
maxVehicleDetectorControlGroups OBJECT-TYPE
    SYNTAX Integer32 (1..255)
    UNITS "group"
    MAX-ACCESS read-only
    STATUS deprecated
    DESCRIPTION "<Definition> The maximum number of vehicle detector control
        groups (8 detectors per group) this device supports. This value is
        equal to TRUNCATE [(maxVehicleDetectors + 7 ) / 8]. This object
        indicates the maximum number of rows which shall appear in the
        vehicleDetectorControlGroupTable object.
    <Object Identifier> 1.3.6.1.4.1.1206.4.2.1.2.11
    <Object Type> S"
    ::= { detector 11 }

--5.3.11  Vehicle Detector Control Group Table
vehicleDetectorControlGroupTable OBJECT-TYPE
    SYNTAX SEQUENCE OF VehicleDetectorControlGroupEntry
    MAX-ACCESS not-accessible
    STATUS current
    DESCRIPTION "<Definition> A table containing vehicle detector control in
        groups of eight detectors. The number of rows in this table is equal
        to the maxVehicleDetectorGroups object.
    <TableType> static
    <Object Identifier> 1.3.6.1.4.1.1206.4.2.1.2.12"
    ::= { detector 12 }

vehicleDetectorControlGroupEntry OBJECT-TYPE
    SYNTAX VehicleDetectorControlGroupEntry
    MAX-ACCESS not-accessible
    STATUS current
    DESCRIPTION "<Definition> A group (row) of vehicle detector controls.
    <Object Identifier> 1.3.6.1.4.1.1206.4.2.1.2.12.1"
    INDEX  { vehicleDetectorControlGroupNumber }
    ::= { vehicleDetectorControlGroupTable  1 }

VehicleDetectorControlGroupEntry ::= SEQUENCE {
    vehicleDetectorControlGroupNumber    Integer32,
    vehicleDetectorControlGroupActuation Integer32 }
     
--5.3.11.1  Vehicle Detector Control Group Number
vehicleDetectorControlGroupNumber OBJECT-TYPE
    SYNTAX Integer32 (1..32)
    UNITS "group"
    MAX-ACCESS not-accessible
    STATUS current
    DESCRIPTION "<Definition> The vehicle detector control group number for
        objects in this row. This value shall not exceed the
        maxVehicleDetectorGroups object value.
    <Object Identifier> 1.3.6.1.4.1.1206.4.2.1.2.12.1.1"
    ::= { vehicleDetectorControlGroupEntry 1 }

--5.3.11.2  Vehicle Detector Control Group Actuation
vehicleDetectorControlGroupActuation OBJECT-TYPE
    SYNTAX Integer32 (0..255)
    MAX-ACCESS read-write
    STATUS current
    DESCRIPTION "<Definition> This object is used to allow a remote entity to
        place an actuation on a vehicle detector. When a bit = 1, an actuation
        is placed on the vehicle detector. When a bit = 0, no actuation is
        placed on the vehicle detector. An NTCIP actuation is placed using
        this object and is treated the same as an external actuation, so all
        detector functions are still applicable, including delay, extension,
        diagnostics, and report objects, such as
        vehicleDetectorStatusGroupActive and volumeOccupancyReport.

        Bit 7: Det # = ( vehicleDetectorControlGroupNumber * 8)
        Bit 6: Det # = ( vehicleDetectorControlGroupNumber * 8) - 1
        Bit 5: Det # = ( vehicleDetectorControlGroupNumber * 8) - 2
        Bit 4: Det # = ( vehicleDetectorControlGroupNumber * 8) - 3
        Bit 3: Det # = ( vehicleDetectorControlGroupNumber * 8) - 4
        Bit 2: Det # = ( vehicleDetectorControlGroupNumber * 8) - 5
        Bit 1: Det # = ( vehicleDetectorControlGroupNumber * 8) - 6
        Bit 0: Det # = ( vehicleDetectorControlGroupNumber * 8) - 7

        The device shall reset this object to ZERO when in BACKUP Mode. A
        write to this object shall reset the Backup timer to ZERO
        (see unitBackupTime).
    <Object Type> C
    <Object Identifier> 1.3.6.1.4.1.1206.4.2.1.2.12.1.2"
    ::= { vehicleDetectorControlGroupEntry 2 }

--5.3.12    Pedestrian Detector Control Group Table
pedestrianDetectorControlGroupTable OBJECT-TYPE
    SYNTAX SEQUENCE OF PedestrianDetectorControlGroupEntry
    MAX-ACCESS not-accessible
    STATUS current
    DESCRIPTION "<Definition> A table containing pedestrian detector control
        in groups of eight detectors. The number of rows in this table is
        equal to the maxPedestrianDetectorGroups object.
    <TableType> static
    <Object Identifier> 1.3.6.1.4.1.1206.4.2.1.2.13"
    ::= { detector 13 }

pedestrianDetectorControlGroupEntry OBJECT-TYPE
    SYNTAX PedestrianDetectorControlGroupEntry
    MAX-ACCESS not-accessible
    STATUS current
    DESCRIPTION "<Definition> A group (row) of pedestrian detector controls.
    <Object Identifier> 1.3.6.1.4.1.1206.4.2.1.2.13.1"
    INDEX  { pedestrianDetectorControlGroupNumber }
    ::= { pedestrianDetectorControlGroupTable  1 }

PedestrianDetectorControlGroupEntry ::= SEQUENCE {
    pedestrianDetectorControlGroupNumber    Integer32,
    pedestrianDetectorControlGroupActuation Integer32 }
     
--5.3.12.1  Pedestrian Detector Control Group Number
pedestrianDetectorControlGroupNumber OBJECT-TYPE
    SYNTAX Integer32 (1..32)
    UNITS "group"
    MAX-ACCESS not-accessible
    STATUS current
    DESCRIPTION "<Definition> The pedestrian detector control group number for
        objects in this row. This value shall not exceed the
        maxPedestrianDetectorGroups object value.
    <Object Identifier> 1.3.6.1.4.1.1206.4.2.1.2.13.1.1"
    ::= { pedestrianDetectorControlGroupEntry 1 }

--5.3.12.2  Pedestrian Detector Control Group Actuation
pedestrianDetectorControlGroupActuation OBJECT-TYPE
    SYNTAX Integer32 (0..255)
    MAX-ACCESS read-write
    STATUS current
    DESCRIPTION "<Definition> This object is used to allow a remote entity to
        place an actuation on a pedestrian detector. When a bit = 1, an
        actuation is placed on the pedestrian detector. When a bit = 0, no
        actuation is placed on the pedestrian detector. An NTCIP actuation is
        placed using this object and is treated the same as an external
        actuation, so all detector functions are still applicable, including
        delay, extension, diagnostics, and report objects, such as
        pedestrianDetectorStatusGroupActive and pedestrianDetectorReport.

        Bit 7: Det # = ( pedestrianDetectorControlGroupNumber * 8)
        Bit 6: Det # = ( pedestrianDetectorControlGroupNumber * 8) - 1
        Bit 5: Det # = ( pedestrianDetectorControlGroupNumber * 8) - 2
        Bit 4: Det # = ( pedestrianDetectorControlGroupNumber * 8) - 3
        Bit 3: Det # = ( pedestrianDetectorControlGroupNumber * 8) - 4
        Bit 2: Det # = ( pedestrianDetectorControlGroupNumber * 8) - 5
        Bit 1: Det # = ( pedestrianDetectorControlGroupNumber * 8) - 6
        Bit 0: Det # = ( pedestrianDetectorControlGroupNumber * 8) - 7

        The device shall reset this object to ZERO when in BACKUP Mode. A
        write to this object shall reset the Backup timer to ZERO
        (see unitBackupTime).
    <Object Identifier> 1.3.6.1.4.1.1206.4.2.1.2.13.1.2
    <Object Type> C"
    ::= { pedestrianDetectorControlGroupEntry 2 }


--5.3.13 Maximum Vehicle Detector Sets
maxVehicleDetectorSets OBJECT-TYPE
    SYNTAX Integer32 (1..255)
    UNITS "set"
    MAX-ACCESS read-only
    STATUS current
    DESCRIPTION "<Definition> The Maximum Number of Vehicle Detector Sets this
        Controller Unit supports. This object indicates the maximum value for
        the vehicleDetectorSetTable index vehicleDetectorSetNumber.
    <Object Identifier> 1.3.6.1.4.1.1206.4.2.1.2.14
    <Object Type> S"
    ::= { detector 14 }

--5.3.14 Vehicle Detector Set Table
vehicleDetectorSetTable OBJECT-TYPE
    SYNTAX SEQUENCE OF VehicleDetectorSetEntry
    MAX-ACCESS not-accessible
    STATUS current
    DESCRIPTION "<Definition> A table containing Controller Unit vehicle
        detector parameters. The number of rows in this table is equal to the
        maxVehicleDetectors object times the maxVehicleDetectorSets object.

        The first set in this table (vehicleDetectorSetNumber = 1) shall match is corresponding objects in the vehicleDetectorTable, unless explicitly defined. 
        For example:
            vehicleDetectorSetOptions.1.n = vehicleDetectorOptions.n
            vehicleDetectorSetCallPhase.1.n = vehicleDetectorCallPhase.n:
            vehicleDetectorSetSwitchPhase.1.n = vehicleDetectorSwitchPhase.n
            etc
            vehicleDetectorSetTravelMode.1.n = vehicleDetectorTravelMode.n
    <TableType> static
    <Object Identifier> 1.3.6.1.4.1.1206.4.2.1.2.15"
    ::= { detector 15 }

vehicleDetectorSetEntry OBJECT-TYPE
    SYNTAX VehicleDetectorSetEntry
    MAX-ACCESS not-accessible
    STATUS current
    DESCRIPTION "<Definition> Parameters for a one of a set of Controller Unit
        detectors.
    <Object Identifier> 1.3.6.1.4.1.1206.4.2.1.2.15.1"
    INDEX   { vehicleDetectorSetNumber, vehicleDetectorNumber }
    ::= { vehicleDetectorSetTable 1 }

VehicleDetectorSetEntry ::= SEQUENCE {
    vehicleDetectorSetNumber                Integer32,
    vehicleDetectorSetOptions               Integer32,
    vehicleDetectorSetCallPhase             Integer32,
    vehicleDetectorSetSwitchPhase           Integer32,
    vehicleDetectorSetDelay                 Integer32,
    vehicleDetectorSetExtend                Integer32,
    vehicleDetectorSetQueueLimit            Integer32,
    vehicleDetectorSetNoActivity            Integer32,
    vehicleDetectorSetMaxPresence           Integer32,
    vehicleDetectorSetErraticCounts         Integer32,
    vehicleDetectorSetFailTime              Integer32,
    vehicleDetectorSetOptions2              Integer32,
    vehicleDetectorSetAvgVehicleLength      Integer32,
    vehicleDetectorSetTravelMode            INTEGER }

--5.3.14.1   Vehicle Detector Set Number
vehicleDetectorSetNumber OBJECT-TYPE
    SYNTAX Integer32 (1..255)
    UNITS "set"
    MAX-ACCESS not-accessible
    STATUS current
    DESCRIPTION "<Definition> The vehicle detector set index for objects in
        this row. The value shall not exceed maxVehicleDetectorSets.
    <Object Identifier> 1.3.6.1.4.1.1206.4.2.1.2.15.1.1"
    ::= { vehicleDetectorSetEntry 1 }

--5.3.14.2   Vehicle Detector Set Options Parameter
vehicleDetectorSetOptions OBJECT-TYPE
    SYNTAX Integer32 (0..255)
    MAX-ACCESS read-write
    STATUS current
    DESCRIPTION "<Definition> Vehicle Detector Set Options Parameter as
        follows (0=Disabled, 1=Enabled):
    Bit 7: Call - if Enabled, the CU shall place a demand for vehicular
        service on the assigned phase when the phase is not timing the green
        interval and an actuation is present.
    Bit 6: Queue - if Enabled, the CU shall extend the green interval of the
        assigned phase until a gap occurs (no actuation) or until the green
        has been active longer than the vehicleDetectorQueueLimit time.
        This is optional.
    Bit 5: AddedInitial - if Enabled, the CU shall accumulate detector
        actuation counts for use in the added initial calculations. Counts
        shall be accumulated from the beginning of the yellow interval to the
        beginning of the green interval.
    Bit 4: Passage - if Enabled, the CU shall maintain a reset to the
        associated phase passage timer for the duration of the detector
        actuation when the phase is green.
    Bit 3: Red Lock Call - if Enabled, the detector will lock a call to the
        assigned phase if an actuation occurs while the phase is not timing
        Green or Yellow. This mode is optional.
    Bit 2: Yellow Lock Call - if Enabled, the detector will lock a call to
        the assigned phase if an actuation occurs while the phase is not
        timing Green.
    Bit 1: Reserved
    Bit 0: Reserved

    A SET of both bits 2 & 3 = 1 shall result in bit 2=1 and bit 3=0.
    <Object Identifier> 1.3.6.1.4.1.1206.4.2.1.2.15.1.2
    <Object Type> P"
    ::= { vehicleDetectorSetEntry 2}

--5.3.14.3   Vehicle Detector Set Call Phase Parameter
vehicleDetectorSetCallPhase OBJECT-TYPE
    SYNTAX Integer32 (0..255)
    UNITS "phase"
    MAX-ACCESS read-write
    STATUS current
    DESCRIPTION "<Definition> This object contains assigned phase number for
        the detector input associated with this row. The associated detector
        call capability is enabled when this object is set to a non-zero
        value. The value shall not exceed the value of maxPhases.
    <Object Identifier> 1.3.6.1.4.1.1206.4.2.1.2.15.1.3
    <Object Type> P"
    REFERENCE "NEMA TS 2 Clause 3.5.5.5.4 and 3.5.5.5.5" 
    ::= { vehicleDetectorSetEntry 3 }

--5.3.14.4   Vehicle Detector Set Switch Phase Parameter
vehicleDetectorSetSwitchPhase OBJECT-TYPE
    SYNTAX Integer32 (0..255)
    UNITS "phase"
    MAX-ACCESS read-write
    STATUS current
    DESCRIPTION "<Definition> Detector Switch Phase Parameter (i.e., Phase
        Number). The phase to which a vehicle detector actuation shall be
        switched when the assigned phase is Yellow or Red and the Switch Phase
        is Green.
    <Object Identifier> 1.3.6.1.4.1.1206.4.2.1.2.15.1.4
    <Object Type> P"
    REFERENCE "NEMA TS 2 Clause 3.5.5.5.4.c"
    ::= { vehicleDetectorSetEntry 4 }

--5.3.14.5   Vehicle Detector Set Delay Parameter
vehicleDetectorSetDelay OBJECT-TYPE
    SYNTAX Integer32 (0..2550)
    UNITS "decisecond"
    MAX-ACCESS read-write
    STATUS current
    DESCRIPTION "<Definition> Detector Delay Parameter in tenth seconds
        (0-255.0 sec). The period a detector actuation (input recognition)
        shall be delayed when the phase is not Green. 
    <Object Identifier> 1.3.6.1.4.1.1206.4.2.1.2.15.1.5
    <Object Type> P"
    REFERENCE "NEMA TS 2 Clause 3.5.5.5.4.a"
    ::= { vehicleDetectorSetEntry 5 }

--5.3.14.6   Vehicle Detector Set Extend Parameter
vehicleDetectorSetExtend OBJECT-TYPE
    SYNTAX Integer32 (0..255)
    UNITS "decisecond"
    MAX-ACCESS read-write
    STATUS current
    DESCRIPTION "<Definition> Detector Extend Parameter in tenth seconds
        (0-25.5 sec). The period a vehicle detector actuation (input duration)
        shall be extended from the point of termination, when the phase is
        Green.
    <Object Identifier> 1.3.6.1.4.1.1206.4.2.1.2.15.1.6
    <Object Type> P"
    REFERENCE "NEMA TS 2 Clause 3.5.5.5.4.b"
    ::= { vehicleDetectorSetEntry 6 }

--5.3.14.7   Vehicle Detector Set Queue Limit
vehicleDetectorSetQueueLimit OBJECT-TYPE
    SYNTAX Integer32 (0..255)
    UNITS "second"
    MAX-ACCESS read-write
    STATUS current
    DESCRIPTION "<Definition> Detector Queue Limit parameter in seconds 
        (0-255 sec). The length of time that an actuation from a queue
        detector may continue into the phase green. This time begins when the
        phase becomes green and when it expires any associated detector inputs
        shall be ignored. This time may be shorter due to other overriding
        device parameters (i.e. Maximum time, Force Offs, ...).
    <Object Identifier> 1.3.6.1.4.1.1206.4.2.1.2.15.1.7
    <Object Type> P"
    ::= { vehicleDetectorSetEntry 7 }

--5.3.14.8   Vehicle Detector Set No Activity Parameter
vehicleDetectorSetNoActivity OBJECT-TYPE
    SYNTAX Integer32 (0..65535)
    UNITS "minute"
    MAX-ACCESS read-write
    STATUS current
    DESCRIPTION "<Definition> Detector No Activity diagnostic Parameter in
        minutes (1-65535 min.). If an active detector does not exhibit an
        actuation in the specified period, it is considered a fault by the
        diagnostics and the detector is classified as Failed. A value of zero for
        this object shall disable this diagnostic for this detector.

    <Object Identifier> 1.3.6.1.4.1.1206.4.2.1.2.15.1.8
    <Object Type> P"
    REFERENCE "NEMA TS 2 Clause 3.9.3.1.4.1"
    ::= { vehicleDetectorSetEntry 8 }

--5.3.14.9   Vehicle Detector Set Maximum Presence Parameter
vehicleDetectorSetMaxPresence OBJECT-TYPE
    SYNTAX Integer32 (0..255)
    UNITS "minute"
    MAX-ACCESS read-write
    STATUS current
    DESCRIPTION "<Definition> Detector Maximum Presence diagnostic Parameter
        in minutes (0-255 min.). If an active detector exhibits continuous
        detection for too long a period, it is considered a fault by the
        diagnostics and the detector is classified as Failed. A value of zero for
        this object shall disable this diagnostic for this detector.

        This object corresponds to the object vehicleDetectorSwitchPhase
        in the vehicleDetectorTable.
    <Object Identifier> 1.3.6.1.4.1.1206.4.2.1.2.15.1.9
    <Object Type> P"
    REFERENCE "NEMA TS 2 Clause 3.9.3.1.4.2"
    ::= { vehicleDetectorSetEntry 9 }

--5.3.14.10  Vehicle Detector Set Erratic Counts Parameter
vehicleDetectorSetErraticCounts OBJECT-TYPE
    SYNTAX Integer32 (0..255)
    UNITS "count"
    MAX-ACCESS read-write
    STATUS current
    DESCRIPTION "<Definition> Detector Erratic Counts diagnostic Parameter in
        counts/minute (0-255 cpm). If an active detector exhibits excessive
        actuations, it is considered a fault by the diagnostics and the
        detector is classified as Failed. A value of zero for this object shall
        disable this diagnostic for this detector.

    <Object Identifier> 1.3.6.1.4.1.1206.4.2.1.2.15.1.10
    <Object Type> P"
    REFERENCE "NEMA TS 2 Clause 3.9.3.1.4.3"
    ::= { vehicleDetectorSetEntry 10 }

--5.3.14.11  Vehicle Detector Set Fail Time Parameter
vehicleDetectorSetFailTime OBJECT-TYPE
    SYNTAX Integer32 (0..255)
    UNITS "second"
    MAX-ACCESS read-write
    STATUS current
    DESCRIPTION "<Definition> Detector Fail Time in seconds (0..255 sec). If a
        detector diagnostic indicates that the associated detector input is
        failed, then a call shall be placed on the associated phase during all
        non-green intervals. When each green interval begins the call shall be
        maintained for the length of time specified by this object and then
        removed. If the value of this object equals the maximum value (255)
        then a constant call shall be placed on the associated phase (max
        recall). If the value of this object equals zero, then no call shall be
        placed on the associated phase for any interval (no recall). Compliant
        devices may support a limited capability for this object (i.e. only
        max recall). At a minimum, the max recall setting must be supported.
    <Object Identifier> 1.3.6.1.4.1.1206.4.2.1.2.15.1.11
    <Object Type> P"
    ::= { vehicleDetectorSetEntry 11 }

-- Note: There is no object corresponding to vehicleDetectorAlarms in vehicleDetectorSetTable

-- Note: There is no object corresponding to vehicleDetectorReportedAlarms in vehicleDetectorSetTable

-- Note: There is no object corresponding to vehicleDetectorReset in vehicleDetectorSetTable

--5.3.14.12  Vehicle Detector Set Options 2
vehicleDetectorSetOptions2 OBJECT-TYPE
    SYNTAX Integer32 (0..255)
    MAX-ACCESS read-write
    STATUS current
    DESCRIPTION "<Definition> A bit-mapped value as defined below for
        configuring detector options.
    <Format>
        Bit 7: Reserved 
        Bit 6: Reserved
        Bit 5: Reserved
        Bit 4: Reserved
        Bit 3: Reserved
        bit 2    0=CUSTOM, 1=NTCIP  Default Detector Speed Mode Option. For a
                    vehicle detector operating in pairs, this option is used
                    when there is an error on one of the paired detectors. It
                    identifies how the controller should calculate speed
                    without the other detector. CUSTOM indicates a
                    manufacturer specific calculation. NTCIP indicates the use
                    of the calculation Speed = (Average Vehicle Length +
                    Detector Length) / Detect Time. 
        bit 1    0=TRAIL, 1=LEAD  Detector Placement Option. For a vehicle
                    detector operating in pairs, this option indicates the
                    leading and trailing detectors. LEAD indicates that the
                    detector is the leading detector of the pair. TRAIL
                    indicates that the detector is a trailing detector in
                    the pair.
        bit 0    0=DISABLED, 1=ENABLED  Enable Speed Data. If enabled, the
                    detector is used to collect speed data (See
                    volumeOccupancyTable and detectorAvgSpeed). This
                    capability may not be supported on all detector inputs to
                    a device.

    <Object Identifier> 1.3.6.1.4.1.1206.4.2.1.2.15.1.12
    <Object Type> P"
    ::= { vehicleDetectorSetEntry 12 }

--Note: There is no object corresponding to vehicleDetectorPairedDetector in vehicleDetectorSetTable

--Note: There is no object corresponding to vehicleDetectorPairedDetectorSpacing in vehicleDetectorSetTable

--5.3.14.13  Vehicle Detector Set Average Vehicle Length
vehicleDetectorSetAvgVehicleLength OBJECT-TYPE
    SYNTAX Integer32 (1..4000)
    UNITS "centimeter"
    MAX-ACCESS read-write
    STATUS current
    DESCRIPTION "<Definition> This parameter allows the user to set the
        average vehicle length for use in determining speed and
        classification. This allows for a range of lengths between 0.01 meters
        to 40 meters in length.

        Different sets may be used to support different vehicle mixes based on time of day, such as cars during rush hour and trucks at night.

    <Object Identifier> 1.3.6.1.4.1.1206.4.2.1.2.15.1.13
    <Object Type> P"
    ::= { vehicleDetectorSetEntry 13 }

-- Note: There is no object corresponding to vehicleDetectorLength in vehicleDetectorSetTable

--5.3.14.14  Vehicle Detector Set Travel Mode
vehicleDetectorSetTravelMode OBJECT-TYPE
    SYNTAX INTEGER { other (1),
                     vehicle (2),
                     transit (3),
                     bicycle (4) }
    MAX-ACCESS read-write
    STATUS current
    DESCRIPTION "<Definition> This parameter allows the user to identify
        detectors for specific types of travel modes.

        other:   refers to a detector for a travel type not defined in this
                    standard
        vehicle: refers to a detector identified for vehicles.
        transit: refers to a detector identified for transit vehicles.
        bicycle: refers to a detector identified for bicycles.
    <Object Identifier> 1.3.6.1.4.1.1206.4.2.1.2.15.1.14
    <Object Type> P"
    DEFVAL { 2 }
    ::= { vehicleDetectorSetEntry 14 }

--5.3.15 Maximum Pedestrian Detector Sets
maxPedestrianDetectorSets OBJECT-TYPE
    SYNTAX Integer32 (1..255)
    UNITS "set"
    MAX-ACCESS read-only
    STATUS current
    DESCRIPTION "<Definition> The Maximum Number of Pedestrian Detector Sets this
        Controller Unit supports. This object indicates the maximum value for
        the PedestrianDetectorSetTable index pedestrianDetectorSetNumber.

    <Object Identifier> 1.3.6.1.4.1.1206.4.2.1.2.16
    <Object Type> S"
    ::= { detector 16 }

--5.3.16 Pedestrian Detector Set Parameter Table
pedestrianDetectorSetTable OBJECT-TYPE
    SYNTAX SEQUENCE OF PedestrianDetectorSetEntry
    MAX-ACCESS not-accessible
    STATUS current
    DESCRIPTION "<Definition> A table containing Controller Unit pedestrian
        detector parameters. The number of rows in this table is equal to the
        maxPedestrianDetectorSets object.

           The first set in this table (pedestrianDetectorSetNumber = 1) shall match is corresponding objects in the pedestrianDetectorTable, unless explicitly defined. 
        For example:
            pedestrianDetectorSetCallPhase.1.n = pedestrianDetectorCallPhase.n:
            pedestrianDetectorSetSwitchPhase.1.n = pedestrianDetectorSwitchPhase.n
            etc, etc
            pedestrianDetectorSetOptions.1.n = pedestrianDetectorOptions.n

    <TableType> static
    <Object Identifier> 1.3.6.1.4.1.1206.4.2.1.2.17"
    ::= { detector 17 }

pedestrianDetectorSetEntry OBJECT-TYPE
    SYNTAX PedestrianDetectorSetEntry
    MAX-ACCESS not-accessible
    STATUS current
    DESCRIPTION "<Definition> Parameters for a specific Controller Unit
        pedestrian detector.
    <Object Identifier> 1.3.6.1.4.1.1206.4.2.1.2.17.1"
    INDEX   { pedestrianDetectorSetNumber, pedestrianDetectorNumber }
    ::= { pedestrianDetectorSetTable 1 }

PedestrianDetectorSetEntry ::= SEQUENCE {
    pedestrianDetectorSetNumber         Integer32,
    pedestrianDetectorSetCallPhase      Integer32,
    pedestrianDetectorSetNoActivity     Integer32,
    pedestrianDetectorSetMaxPresence    Integer32,
    pedestrianDetectorSetErraticCounts  Integer32,
    pedestrianDetectorSetOptions        Integer32 }
 
--5.3.16.1   Pedestrian Detector Set Number
pedestrianDetectorSetNumber OBJECT-TYPE
    SYNTAX Integer32 (1..255)
    UNITS "set"
    MAX-ACCESS not-accessible
    STATUS current
    DESCRIPTION "<Definition> The pedestrianDetector set index for objects in
        this row. The value shall not exceed the maxPedestrianDetectorSets object
        value.
    <Object Identifier> 1.3.6.1.4.1.1206.4.2.1.2.17.1.1"
    ::= { pedestrianDetectorSetEntry 1 }

--5.3.16.2   Pedestrian Detector Set Call Phase Parameter
pedestrianDetectorSetCallPhase OBJECT-TYPE
    SYNTAX Integer32 (0..255)
    UNITS "phase"
    MAX-ACCESS read-write
    STATUS current
    DESCRIPTION "<Definition> This object contains assigned phase number for
        the pedestrian detector input associated with this row. The associated
        detector call capability is enabled when this object is set to a
        non-zero value. The value shall not exceed the value of maxPhases.
        A value of zero indicates no call phase.
    <Object Identifier> 1.3.6.1.4.1.1206.4.2.1.2.17.1.2
    <Object Type> P"
    ::= { pedestrianDetectorSetEntry 2 }

--5.3.16.3   Pedestrian Detector Set No Activity Parameter
pedestrianDetectorSetNoActivity OBJECT-TYPE
    SYNTAX Integer32 (0..65535)
    UNITS "minute"
    MAX-ACCESS read-write
    STATUS current
    DESCRIPTION "<Definition> Pedestrian Detector Set No Activity diagnostic
        Parameter in minutes (1-65535 min.). If an active detector does not
        exhibit an actuation in the specified period, it is considered a fault
        by the diagnostics and the detector is classified as Failed. A value
        of 0 for this object shall disable this diagnostic for this detector.
    <Object Identifier> 1.3.6.1.4.1.1206.4.2.1.2.17.1.3
    <Object Type> P"
    REFERENCE "NEMA TS 2 Clause 3.9.3.1.4.1"
    ::= { pedestrianDetectorSetEntry 3 }

--5.3.16.4   Pedestrian Detector Set Maximum Presence Parameter
pedestrianDetectorSetMaxPresence OBJECT-TYPE
    SYNTAX Integer32 (0..255)
    UNITS "minute"
    MAX-ACCESS read-write
    STATUS current
    DESCRIPTION "<Definition> Pedestrian Detector Set Maximum Presence diagnostic
        Parameter in minutes (0-255 min.). If an active detector exhibits
        continuous detection for too long a period, it is considered a fault
        by the diagnostics and the detector is classified as Failed. A value
        of 0 for this object shall disable this diagnostic for this detector.
    <Object Identifier> 1.3.6.1.4.1.1206.4.2.1.2.17.1.4
    <Object Type> P"
    REFERENCE "NEMA TS 2 Clause 3.9.3.1.4.2"
    ::= { pedestrianDetectorSetEntry 4 }

--5.3.16.5   Pedestrian Detector Set Erratic Counts Parameter
pedestrianDetectorSetErraticCounts OBJECT-TYPE
    SYNTAX Integer32 (0..255)
    UNITS "count"
    MAX-ACCESS read-write
    STATUS current
    DESCRIPTION "<Definition> Pedestrian Detector Set Erratic Counts diagnostic
        Parameter in counts/minute (0-255 cpm). If an active detector exhibits
        excessive actuations, it is considered a fault by the diagnostics and
        the detector is classified as Failed. A value of zero for this object
        shall disable this diagnostic for this detector.
    <Object Identifier> 1.3.6.1.4.1.1206.4.2.1.2.17.1.5
    <Object Type> P"
    REFERENCE "NEMA TS 2 Clause 3.9.3.1.4.3"
    ::= { pedestrianDetectorSetEntry 5 }


-- Note: There is no object corresponding to pedestrianDetectorAlarms in pedestrianDetectorSetTable

-- Note: There is no object corresponding to pedestrianDetectorReset in pedestrianDetectorSetTable

-- Note: There is no object corresponding to pedestrianBushButtonTime in pedestrianDetectorSetTable

--5.3.16.6   Pedestrian Detector Set Options
pedestrianDetectorSetOptions OBJECT-TYPE
    SYNTAX Integer32 (0..255)
    MAX-ACCESS read-write
    STATUS current
    DESCRIPTION " <Definition> Pedestrian Detector Set Options Parameter as
        follows (0=Disabled, 1=Enabled):

        Bit 7: Reserved.
        Bit 6: Reserved.
        Bit 5: Reserved.
        Bit 4: Advanced Walk: If enabled, the detector will place calls for the
                phase's pedestrian WALK indication to start before the phase's
                vehicle GREEN indication. 
        Bit 3: Delayed Walk: If enabled, the detector will place calls for the
                phase's pedestrian WALK indication to start after the phase's
                vehicle GREEN indication. 
        Bit 2: Non-locking: If enabled, detector will place non-locked calls
                instead of locked calls.
        Bit 1: Alternate timing: If enabled, the detector will place calls for
                alternate ped timing instead of normal ped timing.
        Bit 0: Presence: If enabled, the detector indicates presence of
                pedestrians in the crosswalk instead of placing calls for
                service.
        
        A SET of both bits 3 & 4 shall result in bit 3=0 and bit 4=1. A SET of
        a 'reserved' bit to a value other than zero (0) shall return a
        badValue(3) error.
    <Object Identifier> 1.3.6.1.4.1.1206.4.2.1.2.17.1.6
    <Object Type> P"
    DEFVAL { 0 }
    ::= { pedestrianDetectorSetEntry 6 }

--5.3.17  Detector Diagnostics Reset
unitDetectorDiagnosticReset OBJECT-TYPE
    SYNTAX Integer32 (0..1)
    MAX-ACCESS read-write
    STATUS current
    DESCRIPTION "<Definition> This object when set to TRUE (one) shall cause
        the CU to clear detector faults and reset diagnostic counters for ALL
        vehicle and pedestrian detectors. 
        All diagnostic counters with thresholds configured in the following
        objects are reset to zero:
            vehicleDetectorNoActivity or vehicleDetectorSetNoActivity
            vehicleDetectorMaxPresence or vehicleDetectorSetMaxPresence
            vehicleDetectorErraticCounts or vehicleDetectorSetErraticCounts
            pedestrianDetectorNoActivity or pedestrianDetectorSetNoActivity
            pedestrianDetectorMaxPresence or pedestrianDetectorSetMaxPresence
            pedestrianDetectorErraticCounts or pedestrianDetectorSetErraticCounts

        The value of these objects do not change when the diagnostic counters
        are reset. 

        This object shall automatically return to FALSE (zero) after the CU has
        issued the reset command.
        
        This object does not command the CU to reset detectors (see
        vehicleDetectorReset and pedestrianDetectorReset)
    <Object Identifier> 1.3.6.1.4.1.1206.4.2.1.2.2.1.18
    <Object Type> C"
    ::= { detector 18 }

--5.4   Unit Parameters
unit OBJECT IDENTIFIER 
    ::= { asc 3 }

--This defines a node for supporting unit objects.

--5.4.1 Startup Flash Parameter
unitStartUpFlash OBJECT-TYPE
    SYNTAX Integer32 (0..255)
    UNITS "second"
    MAX-ACCESS read-write
    STATUS current
    DESCRIPTION "<Definition> Unit Start up Flash time parameter in seconds
        (0 to 255 sec). The period/state (Start-Up Flash) occurs when power is
        restored following a device defined power interruption. During the
        Start-Up Flash state, the Fault Monitor and Voltage Monitor outputs
        shall be inactive (if present) and the Channel Flash settings shall be
        overridden.
    <Object Identifier> 1.3.6.1.4.1.1206.4.2.1.3.1
    <Object Type> P"
    REFERENCE "NEMA TS 2 Clause 3.9.1.1"
    ::= { unit 1 }
     
--5.4.2 Automatic Ped Clear Parameter
unitAutoPedestrianClear OBJECT-TYPE
    SYNTAX INTEGER { disable(1),
                    enable (2) }
    MAX-ACCESS read-write
    STATUS current
    DESCRIPTION "<Definition> Unit Automatic Ped Clear parameter (1 =
        False/Disable 2=True/Enable). When enabled, the CU shall time the
        Pedestrian Clearance interval when Manual Control Enable is active and
        prevent the Pedestrian Clearance interval from being terminated by the
        Interval Advance input.
    <Object Identifier> 1.3.6.1.4.1.1206.4.2.1.3.2
    <Object Type> P"
    REFERENCE "NEMA TS 2 Clause 3.5.3.10"
    ::= { unit 2 }

--5.4.3 Backup Time Parameter
unitBackupTime OBJECT-TYPE
    SYNTAX Integer32 (0..16777216)
    UNITS "second"
    MAX-ACCESS read-write
    STATUS current
    DESCRIPTION "<Definition> The Backup Time in seconds (0-16777216 sec). When
        any of the defined system control parameters is SET, the backup timer
        is reset. After reset, the CU times the unitBackupTime interval. If the
        unitBackupTime interval expires without a SET operation to any of the
        system control parameters, then the CU shall revert to Backup Mode. 
        
        A value of zero for this object shall disable this feature. 
        
        A SET to this object does NOT reset the backup timer. 

         The system control parameters are: 
            phaseControlGroupPhaseOmit, 
            phaseControlGroupPedOmit, 
            phaseControlGroupHold, 
            phaseControlGroupForceOff, 
            phaseControlGroupVehCall, 
            phaseControlGroupPedCall, 
            systemPatternControl, 
            systemSyncControl, 
            preemptControlState, 
            ringControlGroupStopTime, 
            ringControlGroupForceOff, 
            ringControlGroupMax2, 
            ringControlGroupMaxInhibit, 
            ringControlGroupPedRecycle, 
            ringControlGroupRedRest, 
            ringControlGroupOmitRedClear, 
            unitControlV4, 
            specialFunctionOutputControl,
            ringControlGroupMax3,
            vehicleDetectorControlGroupActuation,
            pedestrianDetectorControlGroupActuation,
            actionPlanControl,
            eclaDataTimestamp,
            eclaRingCurrentPhase,
            eclaRingGreenMinEndTime,
            eclaRingGreenMaxEndTime,
            eclaRingGreenLikelyEndTime,
            eclaRingEndTimeConfidence, and
            eclaRingNextPhase
    <Object Identifier> 1.3.6.1.4.1.1206.4.2.1.3.3 
    <Object Type> P"
    ::= { unit 3 }

--5.4.4 Unit Red Revert Parameter
unitRedRevert OBJECT-TYPE
    SYNTAX Integer32 (0..255)
    UNITS "decisecond"
    MAX-ACCESS read-write
    STATUS current
    DESCRIPTION "<Definition> The red revert in tenth seconds (0.0 - 25.5
        sec). This value shall provide the minimum red revert time for all
        phases (i.e. if it is greater than a phaseRedRevert object value, then
        this value shall be used as the red revert time for the affected
        phase). This object provides a minimum Red indication following the
        Yellow Change interval and prior to the next display of Green on the
        same signal output driver group.
    <Object Identifier> 1.3.6.1.4.1.1206.4.2.1.3.4
    <Object Type> P"
    ::= { unit 4 }

--5.4.5 Unit Control Status
unitControlStatus OBJECT-TYPE
    SYNTAX INTEGER { other (1),
    systemControl (2),
    systemStandby (3),
    backupMode(4),
    manual (5),
    localTimebase (6),
    interconnect (7),
    interconnectBackup (8),
    remoteManualControl (9),
    localManualControl (10) }
    MAX-ACCESS read-only
    STATUS current
    DESCRIPTION "<Definition> The Control Mode for Pattern, Flash, or Free at
        the device:
        other: control by a source other than those listed here.
        systemControl: control by central commands.
        systemStandby: control by local based on central command to use local control.
        backupMode: Backup Mode (see unitBackupTime).
        manual: when coordOperationalMode is not equal to 0. 
        localTimebase: control by the local Time Base.
        interconnect: control by the local Interconnect inputs.
        interconnectBackup: control by local timebase control due to invalid Interconnect inputs or loss of sync.
        remoteManualControl: control by central command via remote MCE commands (See unitMCEIntAdv and unitMCETimeout).
        localManualControl: control via MCE and Interval Advance inputs (e.g., police panel)
    <Object Identifier> 1.3.6.1.4.1.1206.4.2.1.3.5
    <Object Type> S"
    ::= { unit 5 }

--5.4.6 Unit Flash Status
unitFlashStatus OBJECT-TYPE
    SYNTAX INTEGER { other(1),
    notFlash(2),
    automatic(3),
    localManual(4),
    controllerFaultFlash(5),
    smu(6),
    startup(7),
    preempt (8),
    remoteManual(9) }
    MAX-ACCESS read-only
    STATUS current
    DESCRIPTION "<Definition> The Flash modes:

        other: the CU is in flash for some other reason.
        notFlash: the CU is not in Flash 
        automatic: the CU is currently in an Automatic Flash state due to the CU programmed settings. 
        localManual: the Controller Unit Local Flash input is active, MMU
                Flash input is not active, and Flash is not commanded by
                the central system.
        controllerFaultFlash: the CU initiated the Flash State due to a detected fault. 
        smu: the Controller Unit Signal Monitoring Unit Flash input is active and the CU is not
                in Start-Up Flash. This was referred to as an MMU in 1202 v03.  
        start-up: the CU is currently timing the Start-Up Flash period.
        preempt: the CU is currently timing the preempt Flash.
        remoteManual: coordOperationalMode or systemPatternControl is equal to 255.
    <Object Identifier> 1.3.6.1.4.1.1206.4.2.1.3.6
    <Object Type> S"
    ::= { unit 6 }

--5.4.7 Unit Alarm Status 2
unitAlarmStatus2 OBJECT-TYPE
    SYNTAX Integer32 (0..255)
    MAX-ACCESS read-only
    STATUS deprecated
    DESCRIPTION "<Definition> Device Alarm Mask 2 ( 0 = False, 1 = True) as
        follows:

        Bit 7: Process Failure - Whenever the CU detects a process (task)
                failure.
        Bit 6: Stall Condition - Whenever the CU detects a watchdog condition
                on any 'critical' watchdog. A 'critical' watchdog timer is any
                timer for a process or service that may jeopardize the safe
                operation of the ASC.
        Bit 5: Offset Transitioning - Whenever the CU is performing an offset
                transition (correction in process)
        Bit 4: Stop Time - When either CU Stop Time Input becomes active.
        Bit 3: External Start - When the CU External Start becomes active.
        Bit 2: Response Fault - When any NEMA TS2 Port 1 response frame fault
                occurs.
        Bit 1: Low Battery - When any battery voltage falls below the required
                level.
        Bit 0: Power Restart - When power returns after a power interruption.

        Once set, a bit shall maintain its state as long as the condition
        exists. Bit 0 (Power Restart) status shall be maintained until a READ
        of this object occurs.
    <Object Identifier> 1.3.6.1.4.1.1206.4.2.1.3.7
    <Object Type> S"
    ::= { unit 7 }

--5.4.8 Unit Alarm Status 1
unitAlarmStatus1 OBJECT-TYPE
    SYNTAX Integer32 (0..255)
    MAX-ACCESS read-only
    STATUS deprecated
    DESCRIPTION "<Definition> Device Alarm Mask 1 ( 0 = False, 1 = True) as
        follows:

        Bit 7: CoordActive - When coordination is active and not preempted or
                overridden.
        Bit 6: Local Free - When any of the CU inputs and/or programming cause
                it not to run coordination.
        Bit 5: Local Flash - When the Controller Unit Local Flash input
                becomes active, MMU Flash input is not active, and Flash is
                not commanded by the system.
        Bit 4: MMU Flash - When the Controller Unit MMU Flash input remains
                active for a period of time exceeding the Start-Up Flash time.
        Bit 3: Cycle Fail - When a local Controller Unit is operating in the
                non-coordinated mode, whether the result of a Cycle Fault or
                Free being the current normal mode, and cycling diagnostics
                indicate that a serviceable call exists that has not been
                serviced for two cycles.
        Bit 2: Coord Fail - When a Coord Fault is in effect and a Cycle Fault
                occurs again within two cycles of the coordination retry.
        Bit 1: Coord Fault - When a Cycle Fault is in effect and the
                serviceable call has been serviced within two cycles after the
                Cycle Fault.
        Bit 0: Cycle Fault - When the Controller Unit is operating in the
                coordinated mode and cycling diagnostics indicate that a
                serviceable call exists that has not been serviced for two
                cycles.

        Once set, a bit shall maintain its state as long as the condition
        exists.
    <Object Identifier> 1.3.6.1.4.1.1206.4.2.1.3.8
    <Object Type> S"
    ::= { unit 8 }

--5.4.9 Short Alarm Status
shortAlarmStatus OBJECT-TYPE
    SYNTAX Integer32 (0..255)
    MAX-ACCESS read-only
    STATUS deprecated
    DESCRIPTION "<Definition> Short Alarm Mask ( 0 = False, 1 = True) as
        follows:

        Bit 7: Critical Alarm - When the Stop Time input is active.
        Bit 6: Non-Critical Alarm - When an physical alarm input is active.
        Bit 5: Detector Fault - When any detectorAlarm fault occurs.
        Bit 4: Coordination Alarm - When the CU is not running the called
                pattern without offset correction within three cycles of the
                command. An offset correction requiring less than three cycles
                due to cycle overrun caused by servicing a pedestrian call
                shall not cause a Coordination Alarm.
        Bit 3: Local Override - When any of the CU inputs and/or programming
                cause it not to run coordination.
        Bit 2: Local Cycle Zero - When running coordinated and the Coord Cycle
                Status (coordCycleStatus) has passed through zero.
        Bit 1: T&F Flash - When either the Local Flash or MMU Flash input
                becomes active.
        Bit 0: Preempt - When any of the CU Preempt inputs become active.

        Once set, a bit shall maintain its state as long as the condition
        exists. Bit 2 (Local Cycle Zero) status shall be maintained until a
        READ of this object occurs.
    <Object Identifier> 1.3.6.1.4.1.1206.4.2.1.3.9
    <Object Type> S"
    ::= { unit 9 }

--5.4.10    Unit Control
unitControl OBJECT-TYPE
    SYNTAX Integer32 (0..255)
    MAX-ACCESS read-write
    STATUS deprecated
    DESCRIPTION "<Definition> This object is used to allow a remote entity to
        activate unit functions in the device ( 0 = False / Disabled, 1 = True
        / Enabled) as follows:

        Bit 7: Reserved - This bit was used for Dimming Enable in 1202 v03. 
        Bit 6: Interconnect - when set to 1, shall cause the interconnect
                inputs to operate at a higher priority than the timebase
                control (TBC On Line).
                REFERENCE NEMA TS 2 Clause 3.6.2.3 and 3.8.3
        Bit 5: Walk Rest Modifier - when set to 1, causes non-actuated phases
                to remain in the timed-out Walk state (rest in Walk) in the
                absence of a serviceable conflicting call.
                REFERENCE NEMA TS 2 Clause 3.5.5.5.13
        Bit 4: Call to Non-Actuated 2 - when set to 1, causes any phase(s)
                appropriately programmed in the phaseOptions object to operate
                in the Non-Actuated Mode.
                REFERENCE NEMA TS 2 Clause 3.5.5.5.8
        Bit 3: Call to Non-Actuated 1 - when set to 1, causes any phase(s)
                appropriately programmed in the phaseOptions object to operate
                in the Non-Actuated Mode.
                REFERENCE NEMA TS 2 Clause 3.5.5.5.8
        Bit 2: Global Minimum Recall - when set to 1, causes a recurring
                demand on all vehicle phases for a minimum vehicle service.
                REFERENCE NEMA TS 2 Clause 3.5.5.5.9
        Bit 1: Disable Remote Commands - when set to 1, causes a CU to ignore
                commands (all SET requests) from all management station except
                and until this bit is SET to 0 (i.e., a management station can
                still SET this bit to 0 to enable Remote Command).
        Bit 0: Reserved

        When a bit = 1, the device shall activate the Unit control. When a
        bit = 0, the device shall not activate the Unit control.

        A SET of a 'reserved' bit to a value other than zero (0) shall return
        a badValue(3) error.

        The device shall reset this object to ZERO when in BACKUP Mode. A
        write to this object shall reset the BACKUP timer (see unitBackupTime).
    <Object Identifier> 1.3.6.1.4.1.1206.4.2.1.3.10
    <Object Type> P"
    ::= { unit 10 }


--5.4.7    Maximum Alarm Groups
maxAlarmGroups OBJECT-TYPE
    SYNTAX Integer32 (1..32)
    UNITS "group"
    MAX-ACCESS read-only
    STATUS current
    DESCRIPTION "<Definition> This object contains the maximum number of alarm
        groups (8 alarm inputs per group) this device supports. This object
        indicates the maximum rows which shall appear in the alarmGroupTable
        object.
    <Object Identifier> 1.3.6.1.4.1.1206.4.2.1.3.11
    <Object Type> S"
    ::= { unit 11 }

--5.4.8    Alarm Group Table
alarmGroupTable OBJECT-TYPE
    SYNTAX SEQUENCE OF AlarmGroupEntry 
    MAX-ACCESS not-accessible
    STATUS current
    DESCRIPTION "<Definition> This table contains external alarm input status in groups of eight inputs. The number of rows in this table is equal to the
        maxAlarmGroups object.
    <TableType> static
    <Object Identifier> 1.3.6.1.4.1.1206.4.2.1.3.12"
    ::= { unit 12 }

alarmGroupEntry OBJECT-TYPE
    SYNTAX AlarmGroupEntry
    MAX-ACCESS not-accessible
    STATUS current
    DESCRIPTION "<Definition> Status for eight alarm inputs.
    <Object Identifier> 1.3.6.1.4.1.1206.4.2.1.3.12.1"
    INDEX { alarmGroupNumber }
    ::= { alarmGroupTable 1 }

AlarmGroupEntry ::= SEQUENCE {
    alarmGroupNumber    Integer32,
    alarmGroupState     Integer32 }

--5.4.8.1  Alarm Group Number
alarmGroupNumber OBJECT-TYPE
    SYNTAX Integer32 (1..32)
    UNITS "group"
    MAX-ACCESS not-accessible
    STATUS current
    DESCRIPTION "<Definition> The alarm group number for objects in this row.
        This value shall not exceed the maxAlarmGroups object value.
    <Object Identifier> 1.3.6.1.4.1.1206.4.2.1.3.12.1.1"
    ::= { alarmGroupEntry 1 }

--5.4.8.2  Alarm Group State
alarmGroupState OBJECT-TYPE
    SYNTAX Integer32 (0..255)
    MAX-ACCESS read-only
    STATUS current
    DESCRIPTION "<Definition> Alarm input state bit field. When a bit = 1, the
        associated physical alarm input is active. When a bit = 0, the
        associated alarm input is NOT active.

            Bit 7: Alarm Input # = ( alarmGroupNumber * 8)
            Bit 6: Alarm Input # = ( alarmGroupNumber * 8) -1
            Bit 5: Alarm Input # = ( alarmGroupNumber * 8) -2
            Bit 4: Alarm Input # = ( alarmGroupNumber * 8) -3
            Bit 3: Alarm Input # = ( alarmGroupNumber * 8) -4
            Bit 2: Alarm Input # = ( alarmGroupNumber * 8) -5
            Bit 1: Alarm Input # = ( alarmGroupNumber * 8) -6
            Bit 0: Alarm Input # = ( alarmGroupNumber * 8) -7
    <Object Identifier> 1.3.6.1.4.1.1206.4.2.1.3.12.1.2
    <Object Type> S"
    ::= {alarmGroupEntry 2 }

--5.4.9    Maximum Special Function Outputs
maxSpecialFunctionOutputs OBJECT-TYPE
    SYNTAX Integer32 (1..255)
    UNITS "output"
    MAX-ACCESS read-only
    STATUS current
    DESCRIPTION "<Definition> The Maximum Number of Special Functions this Controller Unit supports.
    <Object Identifier> 1.3.6.1.4.1.1206.4.2.1.3.13
    <Object Type> S"
    ::= { unit 13 }

--5.4.10    Special Function Output Table
specialFunctionOutputTable OBJECT-TYPE
    SYNTAX SEQUENCE OF SpecialFunctionOutputEntry
    MAX-ACCESS not-accessible
    STATUS current
    DESCRIPTION "<Definition> A table containing Actuated Controller Unit
        special function output objects. The number of rows in this table is
        equal to the maxSpecialFunctionOutputs object.
    <TableType> static
    <Object Identifier> 1.3.6.1.4.1.1206.4.2.1.3.14"
    ::= { unit 14 }

specialFunctionOutputEntry OBJECT-TYPE
    SYNTAX SpecialFunctionOutputEntry
    MAX-ACCESS not-accessible
    STATUS current
    DESCRIPTION "<Definition> Control for  Actuated Controller Unit system
        special functions.
    <Object Identifier> 1.3.6.1.4.1.1206.4.2.1.3.14.1"
    INDEX   { specialFunctionOutputNumber }
    ::= { specialFunctionOutputTable 1 }

SpecialFunctionOutputEntry ::= SEQUENCE {
    specialFunctionOutputNumber          Integer32,
    specialFunctionOutputState           INTEGER, -- deprecated
    specialFunctionOutputControl         Integer32,
    specialFunctionOutputStatus          Integer32,
    specialFunctionOutputControlSource   BITS   }

--5.4.10.1  Special Function Output Number
specialFunctionOutputNumber OBJECT-TYPE
    SYNTAX Integer32 (1..255)
    UNITS "output"
    MAX-ACCESS not-accessible
    STATUS current
    DESCRIPTION "<Definition> The special function output number associated
        with object in this row. This value shall not exceed the
        maxSpecialFunctionOutputs object value.
    <Object Identifier> 1.3.6.1.4.1.1206.4.2.1.3.14.1.1
    <Object Type> S"
    ::= { specialFunctionOutputEntry 1 }

--5.4.14.2  Special Function Output State
specialFunctionOutputState OBJECT-TYPE 
    SYNTAX Integer32 (0..1)
    MAX-ACCESS read-write
    STATUS deprecated
    DESCRIPTION "<Definition> The special function output (logical or
        physical) on the device may be controlled by this object. When this
        object is non-zero then the associated special function output signal
        shall be ON. When this object is zero then the associated special
        function output signal shall be OFF A read of this object shall
        reflect the current state of the special function output.
    <Object Identifier> 1.3.6.1.4.1.1206.4.2.1.3.14.1.2"
    ::= { specialFunctionOutputEntry  2 }

--5.4.10.2  Special Function Output Control
specialFunctionOutputControl OBJECT-TYPE
    SYNTAX Integer32 (0..1)
    MAX-ACCESS read-write
    STATUS current
    DESCRIPTION "<Definition> The special function output (logical or
        physical) in the device may be controlled by this object. 0 = OFF &
        1 = ON. The device shall reset this object to ZERO when in BACKUP
        Mode.  A write to this object shall reset the BACKUP timer (see
        unitBackupTime).
    <Object Identifier> 1.3.6.1.4.1.1206.4.2.1.3.14.1.3
    <Object Type> C"
    ::= { specialFunctionOutputEntry  3 }

--5.4.10.3  Special Function Output Status
specialFunctionOutputStatus OBJECT-TYPE
    SYNTAX Integer32 (0..1)
    MAX-ACCESS read-only
    STATUS current
    DESCRIPTION "<Definition> The current status (ON-OFF) of the special
        function output (logical or physical) in the device. 0 = OFF & 1 = ON.
    <Object Identifier> 1.3.6.1.4.1.1206.4.2.1.3.14.1.4
    <Object Type> S"
    ::= { specialFunctionOutputEntry  4 }

--5.4.10.4  Special Function Output Control Source
specialFunctionOutputControlSource OBJECT-TYPE
    SYNTAX BITS {   other(0),
                    remote(1),
                    timebase(2),
                    frontPanel(3) }
    MAX-ACCESS read-only
    STATUS current
    DESCRIPTION "<Definition> This object indicates why the special function is active:
    Valid values are:
        Bit 0: Other - the special function was activated from a source not defined in this standard. 
        Bit 1: Remote- the special function was activated remotely through a management station locally or from the central system.
        Bit 2: Timebase - the special function was activated by the scheduler.
        Bit 3: Front Panel: the special function was commanded from the front panel. 
    <Object Identifier> 1.3.6.1.4.1.1206.4.2.1.3.14.1.5
    <Object Type> S"
    ::= { specialFunctionOutputEntry  5 }

--5.4.11    Remote Manual Control Timer
unitMCETimeout OBJECT-TYPE
    SYNTAX Integer32 (0..65535)
    UNITS "second"
    MAX-ACCESS read-write
    STATUS current
    DESCRIPTION "<Definition> This object performs two functions. First, it
        enables manual operation the same as the MCE controller input.

        Second, it serves as a timeout value for a failsafe. If the value is
        non-zero, remote manual control is enabled. When a SET to this object
        is performed, the controller shall load the value into a timer that
        decrements once per second. If the timer reaches zero or if the object
        is SET to zero by the management station, the controller shall
        automatically disable remote manual control. This forces the
        management station to continually refresh this timer to maintain
        remote manual operation. When in remote manual mode, the controller
        should respond exactly as if the MCE input was active.

        This value is the current value of the timer. 
    <Object Identifier> 1.3.6.1.4.1.1206.4.2.1.3.15
    <Object Type> C"
    ::= { unit 15 }

--5.4.12    Remote Manual Control Advance Command
unitMCEIntAdv OBJECT-TYPE
    SYNTAX Integer32 (0..1)
    MAX-ACCESS read-write
    STATUS current
    DESCRIPTION "<Definition> This object acts as a remote interval advance
        function. When SET to 1, the controller will behave as if the Interval
        Advance input (a.k.a. police 'pickle') was toggled. When remote manual
        control mode is enabled (see unitMCETimeout) the controller shall
        advance to the next interval and reset the value of this object to 0.
        If this object is SET to 1 when the controller is not in remote manual
        control mode, the controller shall return a badValue(3).
    <Object Identifier> 1.3.6.1.4.1.1206.4.2.1.3.16
    <Object Type> C"
    ::= { unit 16 }

--5.4.13    ASC Elevation - Antenna Offset
ascElevationOffset OBJECT-TYPE
    SYNTAX Integer32 (0..31)
    UNITS "meter" 
    MAX-ACCESS read-write 
    STATUS current
    DESCRIPTION "<Definition>The offset in height, in meters, from the antenna
        of a GNSS or similar geopositioning device to the base of CU cabinet.
        It is assumed that the antenna is at a height higher than the base of
        the CU structure.

        Values of 0 to 30 provides a range from 0 meters to 30 meters. The
        value of 31 represents unknown.
    <Object Identifier> 1.3.6.1.4.1.1206.4.2.1.3.17
    <Object Type> P" 
    DEFVAL { 31 }
    ::= { unit 17 }

--5.4.14    Startup Flash Mode
unitStartUpFlashMode OBJECT-TYPE
    SYNTAX INTEGER { other(1),
                     automaticFlash (2),
                     cabinetFlash (3),
                     allRedControllerFlash (4) }
    MAX-ACCESS read-write
    STATUS current
    DESCRIPTION "<Definition> Defines the startup flash state for the unit. The
        possible states are:
    
    other: The startup flash state is a state not defined by this standard.
    Automatic Flash: The startup flash state for each signal indication is
        defined by the channelFlash object for each channel.
    Cabinet Flash: Upon startup, the intersection shall flash based on the
        cabinet's internal flash transfer relay configuration. 
    All Red Controller Flash: Upon startup, the intersection shall flash
        all-red regardless of the channelFlash object settings.
    <Object Type> P
    <Object Identifier> 1.3.6.1.4.1.1206.4.2.1.3.18"
    DEFVAL { 2 }
    ::= { unit 18 }

--5.4.19    Backup Timer Parameter - User Defined
unitUserDefinedBackupTime OBJECT-TYPE
    SYNTAX Integer32 (0..16777216)
    UNITS "second"
    MAX-ACCESS read-write
    STATUS deprecated
    DESCRIPTION "<Definition> The Backup Time in seconds (0-16777216 sec) in
        1-second increments. When any of the user-defined system control
        parameters is SET, the user-defined backup timer is reset. After reset,
        the CU times the unitUserDefinedBackupTime period. If the
        unitUserDefinedBackupTime period expires without a SET operation to any
        of the user-defined control parameters defined in
        unitUserDefinedBackupTimeContent, then the CU reverts to Backup Mode.

        A value of zero (0) for this object shall disable this feature.

        If the value of this object is non-zero, then all functionality related
        to unitBackupTime is disabled.
    <Object Identifier> 1.3.6.1.4.1.1206.4.2.1.3.19
    <Object Type> P"
    DEFVAL {300}
    ::= { unit 19 }

--5.4.20    Maximum Number of User Definable OIDs for Backup Timer
maxUserDefinedBackupTimeContent OBJECT-TYPE
    SYNTAX Integer32 (2..255)
    MAX-ACCESS read-only
    STATUS deprecated
    DESCRIPTION  "<Definition> The Maximum Number of user defined functions to this controller allows for to be subject to unitBackUpTime. This object indicates the maximum rows which shall appear in the unitUserDefinedBackupTimeContentTable object.
    <Object Identifier> 1.3.6.1.4.1.1206.4.2.1.3.20
    <Object Type> S"
    ::= { unit 20 }

--5.4.21    Backup Time - User Defined Functions Table
unitUserDefinedBackupTimeContentTable OBJECT-TYPE
    SYNTAX SEQUENCE OF UnitUserDefinedBackupTimeContentEntry
    MAX-ACCESS not-accessible
    STATUS deprecated
    DESCRIPTION "<Definition> A table containing the parameters of the user defined parameters for the backup timer. All functions defined in this table are subject to the backup timer in addition to the ones defined in unitBackUpTime.
    <TableType> static
    <Object Identifier> 1.3.6.1.4.1.1206.4.2.1.3.21"
    ::= { unit 21 }

unitUserDefinedBackupTimeContentEntry OBJECT-TYPE
    SYNTAX UnitUserDefinedBackupTimeContentEntry
    MAX-ACCESS not-accessible
    STATUS deprecated
    DESCRIPTION "<Definition> Parameters for a user-defined backup timer.
    <Object Identifier> 1.3.6.1.4.1.1206.4.2.1.3.21.1"
    INDEX   { unitUserDefinedBackupTimeContentNumber }
    ::= { unitUserDefinedBackupTimeContentTable 1 }

UnitUserDefinedBackupTimeContentEntry ::= SEQUENCE { 
    unitUserDefinedBackupTimeContentNumber      INTEGER, --deprecated
    unitUserDefinedBackupTimeContentOID         OBJECT IDENTIFIER,--deprecated
    unitUserDefinedBackupTimeContentDescription SnmpAdminString }--deprecated

--5.4.21.1  Backup Time - User Defined Number
unitUserDefinedBackupTimeContentNumber OBJECT-TYPE
    SYNTAX Integer32 (1..65535)
    MAX-ACCESS not-accessible
    STATUS deprecated
    DESCRIPTION "<Definition> A userDefinedBackupTimeContent number for objects in this row. The value shall not exceed maxUserDefinedBackupTimeContents object value.
    <Object Identifier> 1.3.6.1.4.1.1206.4.2.1.3.21.1.1
    <Object Type> S"
    ::= { unitUserDefinedBackupTimeContentEntry 1 }

--5.4.21.2  Backup Time - User Defined OID
unitUserDefinedBackupTimeContentOID OBJECT-TYPE
    SYNTAX OBJECT IDENTIFIER
    MAX-ACCESS read-write
    STATUS deprecated
    DESCRIPTION "<Definition> This object contains a reference to the function, which, if any SET operation is  performed on it, leads to a reset of the timer associated with the unitBackupTime object. This object shall reference the function by its associated identifier including its instance (i.e., the full OID of the scalar or columnar object).
    <Object Identifier> 1.3.6.1.4.1.1206.4.2.1.3.21.1.2
    <Object Type> P"
    DEFVAL { zeroDotZero }
    ::= { unitUserDefinedBackupTimeContentEntry 2 }

--5.4.21.3  Backup Time - User Defined Content Description
unitUserDefinedBackupTimeContentDescription OBJECT-TYPE
    SYNTAX SnmpAdminString
    MAX-ACCESS read-write
    STATUS deprecated
    DESCRIPTION "<Definition> Contains a text description of the referenced function that, if performing a SET command against its corresponding object, will reset the timer associated with the unitDefinedBackupTime object.
    <Object Identifier> 1.3.6.1.4.1.1206.4.2.1.3.21.1.3
    <Object Type> P"
    DEFVAL { "" }
    ::= { unitUserDefinedBackupTimeContentEntry 3 }

--5.4.22    ASC Clock
ascClock OBJECT IDENTIFIER --deprecated
    ::= { unit 22 }


-- This note contains the objects necessary to support time sources.

--5.4.22.1  Maximum Number of Time Sources
maxTimeSources OBJECT-TYPE
    SYNTAX Integer32 (1..255)
    UNITS "timeSource"
    MAX-ACCESS read-only
    STATUS deprecated
    DESCRIPTION "<Definition> The maximum number of time sources that this Controller Unit supports. This object indicates the maximum rows which shall appear in the unitTimeTable object.
    <Object Identifier> 1.3.6.1.4.1.1206.4.2.1.3.22.1
    <Object Type> S"
    ::= { ascClock 1 }

--5.4.22.2  Unit Time Source Table
unitTimeTable OBJECT-TYPE
    SYNTAX SEQUENCE OF UnitTimeEntry
    MAX-ACCESS not-accessible
    STATUS deprecated
    DESCRIPTION "<Definition> A table containing Controller Unit time sources. The number of rows in this table is equal to the maxTimeSources object.
    <TableType> static
    <Object Identifier> 1.3.6.1.4.1.1206.4.2.1.3.22.2"
    ::= { ascClock 2 }

unitTimeEntry OBJECT-TYPE
    SYNTAX UnitTimeEntry
    MAX-ACCESS not-accessible
    STATUS deprecated
    DESCRIPTION "<Definition> Parameters for a specific Controller Unit time source.
    <Object Identifier> 1.3.6.1.4.1.1206.4.2.1.3.22.2.1"
    INDEX { unitTimeIndex }
    ::= { unitTimeTable 1 }

UnitTimeEntry ::= SEQUENCE {
    unitTimeIndex           INTEGER,
    unitTimeSourceAvailable INTEGER }

--5.4.22.2.1    Unit Time Source Index
unitTimeIndex OBJECT-TYPE
    SYNTAX Integer32 (1..255)
    UNITS "timeSource"
    MAX-ACCESS not-accessible
    STATUS deprecated
    DESCRIPTION "<Definition> The index number for objects in this row. The value shall not exceed the maxTimeSources object value.
    <Object Identifier> 1.3.6.1.4.1.1206.4.2.1.3.22.2.1.1
    <Object Type> S"
    ::= { unitTimeEntry 1 }

--5.4.22.2.2    Unit Time Source
unitTimeSourceAvailable OBJECT-TYPE
    SYNTAX INTEGER { other (1),
    lineSync (2),
rtcSqwr (3),
    crystal (4),
    gnss (5),
ntp (6) }
    MAX-ACCESS read-only
    STATUS deprecated
    DESCRIPTION "<Definition> An enumerated value representing the available sources for adjusting the clock. This object sets up the clock sources available for use by the CU.
other: the source of the unit time is not defined by this standard.
lineSync: the source of the unit time is determined by tracking the (AC) power line frequency
rtcSqwr: the source of the unit time a Real Time Clock Square Wave output
crystal: the source of the unit time is the internal crystal. This might also be used if the unit time normally uses line frequency but appears to be drifting too much as might happen when on a power generator.
gnss: a GNSS device is being used to update the unit's internal reference on a frequent basis (e.g., once per minute))
ntp: the network time protocol (NTP) is being used to update the unit's internal reference
    <Object Identifier> 1.3.6.1.4.1.1206.4.2.1.3.22.2.1.2
    <Object Type> S"
    DEFVAL { lineSync }
    ::= { unitTimeEntry 2 }

--5.4.22.3  ASC Clock Source - Commanded
unitTimeSourceCommanded OBJECT-TYPE
    SYNTAX INTEGER { other (1),
    lineSync (2),
    rtcSqwr (3),
    crystal (4),
    gnss (5),
    ntp (6) }
    MAX-ACCESS read-write
    STATUS deprecated
    DESCRIPTION "<Definition>  Commands the unit to the primary source for adjusting the unit clock:
other: the source of the unit time is not defined by this standard.
lineSync: the source of the unit time is determined by tracking the (AC) power line frequency
rtcSqwr: the source of the unit time a Real Time Clock Square Wave output
crystal: the source of the unit time is the internal crystal. This might also be used if the unit time normally uses line frequency but appears to be drifting too much as might happen when on a power generator.
gnss: a GNSS device is being used to update the unit's internal reference on a frequent basis (e.g., once per minute))
ntp: the network time protocol (NTP) is being used to update the unit's internal reference
    <Object Identifier> 1.3.6.1.4.1.1206.4.2.1.3.22.3
    <Object Type> P"
    DEFVAL { lineSync }
    ::= { ascClock 3 }

--5.4.22.4  ASC Clock Source - Current
unitTimeSourceCurrent OBJECT-TYPE
    SYNTAX INTEGER { other (1),
                   lineSync (2),
                   rtcSqwr (3),
                   crystal (4),
                   gnss (5),
                   ntp (6) }
    MAX-ACCESS read-only
    STATUS deprecated
    DESCRIPTION "<Definition> An enumerated value representing the current source for adjusting the unit clock as follows:
other: the source of the unit time is not defined by this standard.
lineSync: the source of the unit time is determined by tracking the (AC) power line frequency
rtcSqwr: the source of the unit time is a Real Time Clock Square Wave output
crystal: the source of the unit time is the internal crystal. This might also be used if the unit time normally uses line frequency but appears to be drifting too much as might happen when on a power generator.
gnss: a GNSS device is being used to update the unit's internal reference on a frequent basis (e.g., once per minute))
ntp: the network time protocol (NTP) is being used to update the unit's internal reference
    <Object Identifier> 1.3.6.1.4.1.1206.4.2.1.3.22.4
    <Object Type> S"
    DEFVAL { lineSync }
    ::= { ascClock 4 }

--5.4.22.5  Unit Time Source Status
unitTimeSourceStatus OBJECT-TYPE
    SYNTAX INTEGER { notActive (1),
                  active (2),
                  dataError (3),
                  dataTimeOutError (4),
                  pendingUpdate (5),
                  nonSequential (6) }
    MAX-ACCESS read-only
    STATUS deprecated
    DESCRIPTION "<Definition>  An enumerated value representing the status of the current unit clock source (unitTimeSourceCurrent).
    notActive: The unit is not monitoring this clock source, or updates are not available.
active: The unit is receiving valid updates and is updating the controller time without errors.
dataError: A data error, such as a crc mismatch, was detected.
dataTimeoutError: No data has been received from the unitTimeSourceCurrent within a reasonable amount of time. This timeout will be preset by the driver for this time source as it depends on the specific implementation.
pendingUpdate: The unit is pending an update from the unitTimeSourceCurrent, such as when the controller is in the startup period and is waiting for the external device to sync to its reference and send the time to the unit.
nonSequential: A non-sequential clock change occurrence. Note this value should be cleared upon reading it (i.e., a GET on this object) or 10 seconds after its occurrence, whichever comes first.
    <Object Identifier> 1.3.6.1.4.1.1206.4.2.1.3.22.5
    <Object Type> S"
    ::= { ascClock 5 }

--5.4.22.6  ASC Clock Non-Sequential Time Source
unitTimeNonSequentialSource OBJECT-TYPE
    SYNTAX INTEGER { unknown (1),
dstChange (2),
managementStation (3),
localUser (4),
timeSourceChange (5),
timeSourceDiscontinuity (6) }
    MAX-ACCESS read-only
    STATUS deprecated
    DESCRIPTION "<Definition> An enumerated value that indicates the source of a non-sequential change to the ASC clock time. A non-sequential change occurs anytime the clock changes by more than 1 increment (whether in seconds or milliseconds).
unknown: the source of the non-sequential change to the unit time is unknown or cannot be determined.
dstChange: the source of the non-sequential change to the unit time is a change in daytime savings time.
managementStation: the source of the non-sequential change to the unit time is a command from a management station.
localUser: the source of the non-sequential change to the unit time is a command from a user or device at the controller unit.
timeSourceChange: A change in the time source (e.g., external1)
timeSourceDiscontinuity: A change as determined by an external time source (e.g., GNSS).
The value is latched until another non-sequential change to the ASC clock time or until the ASC is powered off.
If a non-sequential change occurs or globalTime is SET, then the event should be logged. This object is used with the unitTimeNonSequentialChange and the unitTimeNonSequentialDelta objects.
    <Object Identifier> 1.3.6.1.4.1.1206.4.2.1.3.22.6
    <Object Type> S"
    DEFVAL { unknown }
    ::= { ascClock 6 }

--5.4.22.7  ASC Clock Non-Sequential Time Change 
unitTimeNonSequentialChange OBJECT-TYPE
    SYNTAX Counter32
    UNITS "second"
    MAX-ACCESS read-only
    STATUS deprecated
    DESCRIPTION "<Definition> The 'new' globalTime after a non-sequential change to the ASC clock time. A non-sequential change occurs anytime the clock changes by more than 1 increment (whether in seconds or milliseconds). The value of this object is number of seconds since the epoch of 00:00:00 (midnight) January 1, 1970 UTC (a.k.a. Zulu or GMT).
    <Object Identifier> 1.3.6.1.4.1.1206.4.2.1.3.22.7
    <Object Type> S"
    DEFVAL { 0 }
    ::= { ascClock 7 }

--5.4.22.8  ASC Clock Non-Sequential Time Difference
unitTimeNonSequentialDelta OBJECT-TYPE
    SYNTAX OCTET STRING (SIZE(0 | 5))
    MAX-ACCESS read-only
    STATUS deprecated
    DESCRIPTION
        "<Definition> An octet string indicating the difference between the
        'expected' time and the new time for the ASC clock after a
        non-sequential change to the ASC clock. A non-sequential change occurs
        anytime the clock changes by more than 1 increment (whether in seconds
        or milliseconds). A positive value indicates time jumped ahead while a
        negative value indicates time jumped back. The first octet is from -23
        to +23 hours, the second octet is in minutes, the third octet
        represents seconds, and the last two octets represents milliseconds.

        This object is used with the unitTimeNonSequentialSource and the
        unitTimeNonSequentialChange objects.
    <Object Identifier> 1.3.6.1.4.1.1206.4.2.1.3.22.8
    <Object Type> S"
    DEFVAL { "" }
    ::= { ascClock 8 }

--5.4.15    Communications
commPorts OBJECT IDENTIFIER 
    ::= { unit 23 }

-- This node shall contain objects that configure, monitor or control communications ports functions for this device.

--5.4.15.1  Maximum Communications Ports
maxCommPorts OBJECT-TYPE
    SYNTAX Integer32 (1..16)
    UNITS "port"
    MAX-ACCESS read-only
    STATUS current
    DESCRIPTION "<Definition> The Maximum Number of communications Ports this device supports and is the maximum value of ifNumber allowed.
    <Object Identifier> 1.3.6.1.4.1.1206.4.2.1.3.23.1
    <Object Type> S"
    ::= { commPorts 1 }

--5.4.15.2  Communications Ports Table
commPortsTable OBJECT-TYPE
    SYNTAX SEQUENCE OF CommPortsEntry
    MAX-ACCESS not-accessible
    STATUS current
    DESCRIPTION "<Definition> A table used to describe and configure the communication ports on the CU. The number of rows in this table is equal to the maxCommPorts object.
    <TableType> static
    <Object Identifier> 1.3.6.1.4.1.1206.4.2.1.3.23.2"
    ::= { commPorts 2 }

commPortsEntry OBJECT-TYPE
    SYNTAX CommPortsEntry
    MAX-ACCESS not-accessible
    STATUS current
    DESCRIPTION "<Definition> This object defines a row in the Communication Ports Table which is used to extend the ifTable of RFC 1213. It uses ifIndex from RFC 1213 as the index, so all communications ports in the controller has to be included in the ifTable including async RS232 ports which are also in the rs232PortTable.
    <Object Identifier> 1.3.6.1.4.1.1206.4.2.1.3.23.2.1"
    INDEX { ifIndex }
    ::= { commPortsTable 1 }

CommPortsEntry ::= SEQUENCE { 
    commPortType                INTEGER,
    commPortTypeIndex           Integer32,
    commPortEnable              INTEGER,
    commPortProtocolsSupported  Unsigned32,--deprecated
    commPortProtocol            Integer32,--deprecated
    commPortDiagnostics         INTEGER }--deprecated

--5.4.15.2.1    Communications Port Type
commPortType OBJECT-TYPE
    SYNTAX INTEGER { other (1),
    ethernet (2),
    rs232like (3) }
    MAX-ACCESS read-only
    STATUS current
    DESCRIPTION "<Definition> This object identifies the port type. Although RFC 1213 contains ifType, this object provides the user/device further guidance to additional objects that define the port and its configuration. The valid port types are defined as follows:
other: the port type is not defined by this standard.
Ethernet: the port type is Ethernet based (i.e. IP) and configured per NTCIP 2104 and 2202
rs232like: the port type is rs-232-like (per RFC 1317) and may be either an asynchronous or synchronous serial. Port configuration is contained in RFC 1317 rs232PortTable
    <Object Identifier> 1.3.6.1.4.1.1206.4.2.1.3.23.2.1.1
    <Object Type> S"
    ::= { commPortsEntry 1 }

--5.4.15.2.2    Communications Port Type Number Parameter
commPortTypeIndex OBJECT-TYPE
    SYNTAX Integer32
    MAX-ACCESS read-write
    STATUS current
    DESCRIPTION "<Definition> This object contains the value to be used as the index into the appropriate communication port configuration table. If commPortType = rs232like, then this value is used for RFC 1317 rs232PortIndex into the rs232PortTable. If commPortType is ethernet then this object is redundant and should have the same value as ifIndex.
    <Object Identifier> 1.3.6.1.4.1.1206.4.2.1.3.23.2.1.2
    <Object Type> S"
    ::= { commPortsEntry 2 }

--5.4.15.2.3    Communications Port Enable
commPortEnable OBJECT-TYPE
    SYNTAX INTEGER { enabled (1),
                disabled (2) }
    MAX-ACCESS read-write
    STATUS current
    DESCRIPTION "<Definition> This object is used to enable/disable a communications port on the device unless prohibited by the hardware specification or hardware standard. Unused communications port numbers shall be set to disabled (2), and by default, all available communications ports shall be disabled. A GET of this object returns the current state of the port.

Note that the device may include other means to disable a communications port (e.g. Port 1 Disable input). Attempting to enable a port that is disabled by these other means will fail and a subsequent GET of this object will indicate that the port is still disabled.
    <Object Identifier> 1.3.6.1.4.1.1206.4.2.1.3.23.2.1.3
    <Object Type> C"
    ::= { commPortsEntry 3 }

--5.4.23.2.4    Communications Port Protocol Supported
commPortProtocolsSupported OBJECT-TYPE
    SYNTAX Unsigned32 (0..4294967295) -- v04 check Make unsigned or reduce range to 2147483647 ???
    MAX-ACCESS read-only
    STATUS deprecated
    DESCRIPTION "<Definition> This object identifies the protocols supported by the port. If a protocol is supported on the port, then the bit is set to 1, otherwise the bit is set to zero (0).
    Bits 6 - 31: Reserved
    Bit 5: Console
    Bit 4: Serial Bus #3
    Bit 3: Serial Bus #1
    Bit 2: Port 1
    Bit 1: NTCIP
    Bit 0: Other protocol not defined in this standard
A SET of a 'reserved' bit to a value other than zero (0) shall return a badValue(3) error.
    <Object Identifier> 1.3.6.1.4.1.1206.4.2.1.3.23.2.1.4
    <Object Type> S"
    ::= { commPortsEntry 4 }

--5.4.23.2.5    Communications Port Protocol 
commPortProtocol OBJECT-TYPE
    SYNTAX Integer32 (0..32)
    MAX-ACCESS read-write
    STATUS deprecated
    DESCRIPTION "<Definition> This object specifies the protocol to be used on the communication port. If the port is disabled by means other than commPortEnable or has not yet been initialized, then the protocol shall be zero (0); otherwise the value shall be set to n+1 where n is the bit number within commPortProtocolsSupported of the protocol desired. Note that one can only choose from the set of protocols supported on that port; all other values will return a badValue response.
    <Object Identifier> 1.3.6.1.4.1.1206.4.2.1.3.23.2.1.5
    <Object Type> P"
    ::= { commPortsEntry 5 }

--5.4.23.2.6    Communications Port Diagnostics
commPortDiagnostics OBJECT-TYPE
    SYNTAX INTEGER { normal (1),
        loopback (2),
        echomode (3) }
    MAX-ACCESS read-write
    STATUS deprecated
    DESCRIPTION "<Definition> This object specifies the port diagnostic commands for a communication port. It works in conjunction with ifOperStatus and ifAdminStatus from RFC 1213. Setting this object to loopback or echomode will result in ifAdminStatus being set to 'testing' and if successful the device will update ifOperStatus to testing. When ifAdminStatus is set to either 'up' or 'down', if successful the device will update ifOperStatus accordingly and set this object to 'normal'. One cannot directly set this object to 'normal'.

Note that a user can enable/disable each communications port on the  device unless prohibited by the PRL or hardware standard/specification. Unused communications port numbers shall be set to disabled ('down'), and by default, all available communications ports shall be enabled.
 
Note that the device may include other means to disable a communications port (e.g. Port 1 Disable input). Attempting to enable a port that is disabled by these other means will fail and a subsequent GET of this object will indicate that the port is still disabled. 
    <Object Identifier> 1.3.6.1.4.1.1206.4.2.1.3.23.2.1.6
    <Object Type> P"
    ::= { commPortsEntry 6 }

--5.4.23.3  Maximum Ethernet Ports
maxEthernetPorts OBJECT-TYPE
    SYNTAX Integer32 (1..255)
    UNITS "ethernetPort"
    MAX-ACCESS read-only
    STATUS deprecated
    DESCRIPTION  "<Definition> The Maximum Number of Ethernet communications ports this device supports. This object indicates the maximum rows which shall appear in the ethernetConfigTable object.
    <Object Identifier> 1.3.6.1.4.1.1206.4.2.1.3.23.3
    <Object Type> S"
    ::= { commPorts 3 }

--5.4.23.4  Ethernet Port Configuration Table
ethernetConfigTable OBJECT-TYPE
    SYNTAX SEQUENCE OF EthernetConfigEntry
    MAX-ACCESS not-accessible
    STATUS deprecated
    DESCRIPTION "<Definition> This table extends configurations for the Ethernet ports on the device by providing objects that extend standard configuration tables such as those contained in RFC 1213. 
      The number of rows in this table is equal to the maxEthernetPorts object. This table only contains rows for communication ports with commPortType = ethernet (2).
    Note that the Ethernet port's MAC address can be found via the ifPhysAddress object in the ifTable at the same value of ifIndex.
    <TableType> static
    <Object Identifier> 1.3.6.1.4.1.1206.4.2.1.3.23.4"
    ::= { commPorts 4 }

ethernetConfigEntry OBJECT-TYPE
    SYNTAX EthernetConfigEntry
    MAX-ACCESS not-accessible
    STATUS current
    DESCRIPTION "<Definition> This object defines a row in the Ethernet Port Configuration Table.
    <Object Identifier> 1.3.6.1.4.1.1206.4.2.1.3.23.4.1"
    INDEX { ifIndex }
    ::= { ethernetConfigTable  1 }

EthernetConfigEntry ::= SEQUENCE {
    ecfgIpAddr        IpAddress,--deprecated
    ecfgNetMask       IpAddress,--deprecated
    ecfgGateway       IpAddress,--deprecated
    ecfgDNS           IpAddress,--deprecated
    ecfgMode          INTEGER,--deprecated
    ecfgLogicalName   OCTET STRING,--deprecated
    ecfgStaticIpAddr  IpAddress,--deprecated
    ecfgStaticNetMask IpAddress,--deprecated
    ecfgStaticGateway IpAddress,--deprecated
    ecfgStaticDNS     IpAddress }--deprecated

--5.4.23.4.1    IP Address Parameter
ecfgIpAddr OBJECT-TYPE
    SYNTAX IpAddress
    MAX-ACCESS read-only
    STATUS deprecated
    DESCRIPTION "<Definition> This object contains the IP address of this logical Ethernet Port.
    <Object Identifier> 1.3.6.1.4.1.1206.4.2.1.3.23.4.1.1
    <Object Type> S"
    ::= { ethernetConfigEntry 1 }

--5.4.23.4.2    Net Mask Parameter
ecfgNetMask OBJECT-TYPE
    SYNTAX IpAddress
    MAX-ACCESS read-only
    STATUS deprecated
    DESCRIPTION "<Definition> This object contains the network mask for this Ethernet Port.
    <Object Identifier> 1.3.6.1.4.1.1206.4.2.1.3.23.4.1.2
    <Object Type> S"
    ::= { ethernetConfigEntry 2 }

--5.4.23.4.3    Gateway Parameter
ecfgGateway OBJECT-TYPE
    SYNTAX IpAddress
    MAX-ACCESS read-only
    STATUS deprecated
    DESCRIPTION "<Definition> This object contains the gateway IP address for this Ethernet Port.
    <Object Identifier> 1.3.6.1.4.1.1206.4.2.1.3.23.4.1.3
    <Object Type> S"
    ::= { ethernetConfigEntry 3 }

--5.4.23.4.4    Domain Name Server Parameter
ecfgDNS OBJECT-TYPE
    SYNTAX IpAddress
    MAX-ACCESS read-only
    STATUS deprecated
    DESCRIPTION "<Definition> This object contains the domain name server IP address for this Ethernet Port.
    <Object Identifier> 1.3.6.1.4.1.1206.4.2.1.3.23.4.1.4
    <Object Type> S"
    ::= { ethernetConfigEntry 4 }

--5.4.23.4.5    Ethernet Configuration Mode Parameter
ecfgMode OBJECT-TYPE
    SYNTAX INTEGER { other (1),
static (2),
dHCPclient (3)  }
    MAX-ACCESS read-write
    STATUS deprecated
    DESCRIPTION "<Definition> This object determines how the IPv4 interface is configured:
other: the interface is configured with some other mechanism not defined by this standard
static: the interface is configured using the static values in this table
dHCPclient: the interface is configured via DHCP request
    <Object Identifier> 1.3.6.1.4.1.1206.4.2.1.3.23.4.1.5
    <Object Type> P"
    ::= { ethernetConfigEntry 5 }

--5.4.23.4.6    DHCP Logical Name Parameter
ecfgLogicalName OBJECT-TYPE
    SYNTAX OCTET STRING
    MAX-ACCESS read-write
    STATUS deprecated
    DESCRIPTION "<Definition> This object contains the Logical Name used for this port if DHCP client is enabled. If DHCP client is disabled then this object contains the last Logical Name used for this port (if none, then the object would be a zero length octet string).
    <Object Identifier> 1.3.6.1.4.1.1206.4.2.1.3.23.4.1.6
    <Object Type> P"
    ::= { ethernetConfigEntry 6 }

--5.4.23.4.7    Static IP Address Parameter
ecfgStaticIpAddr OBJECT-TYPE
    SYNTAX IpAddress
    MAX-ACCESS read-write
    STATUS deprecated
    DESCRIPTION "<Definition> This object contains the IP address to be used for  this logical Ethernet Port if the ecfgMode object is static (2).
    <Object Identifier> 1.3.6.1.4.1.1206.4.2.1.3.23.4.1.7"
    ::= { ethernetConfigEntry 7 }

--5.4.23.4.8    Static Net Mask Parameter
ecfgStaticNetMask OBJECT-TYPE
    SYNTAX IpAddress
    MAX-ACCESS read-write
    STATUS deprecated
    DESCRIPTION "<Definition> This object contains the network mask to be used for this Ethernet Port if the ecfgMode object is static (2).
    <Object Identifier> 1.3.6.1.4.1.1206.4.2.1.3.23.4.1.8
    <Object Type> P"
    ::= { ethernetConfigEntry 8 }

--5.4.23.4.9    Static Gateway Parameter
ecfgStaticGateway OBJECT-TYPE
    SYNTAX IpAddress
    MAX-ACCESS read-write
    STATUS deprecated
    DESCRIPTION "<Definition> This object contains the gateway IP address to be used for this Ethernet Port if the ecfgMode object is static (2).
    <Object Identifier> 1.3.6.1.4.1.1206.4.2.1.3.23.4.1.9
    <Object Type> P"
    ::= { ethernetConfigEntry 9 }

--5.4.23.4.10   Static Domain Name Server Parameter
ecfgStaticDNS OBJECT-TYPE
    SYNTAX IpAddress
    MAX-ACCESS read-write
    STATUS deprecated
    DESCRIPTION "<Definition> This object contains the domain name server IP address to be used for this Ethernet Port if the ecfgMode object is static (2).
    <Object Identifier> 1.3.6.1.4.1.1206.4.2.1.3.23.4.1.10
    <Object Type> P"
    ::= { ethernetConfigEntry 10 }

--5.4.23.5  Ethernet Communications Ports
-- To support the Ethernet protocol running at any of the 
-- defined communications ports, the object definitions
-- contained in the following tables within 
-- Annex I shall be supported:
--             SNMP Group
--             System Group
--             Interfaces Group
--             IP Group
--             ICMP Group
--             TCP Group
--             UDP Group
--             Ethernet Group
-- See Annex I for object definitions to be supported. 

--5.4.23.6  Asynchronous RS-232 Communications Ports
-- To support the asynchronous, serial protocol running at 
-- any of the defined communications ports, the object 
-- definitions contained in the following tables within 
-- Annex I shall be supported:
--             SNMP Group
--             System Group
--             RS232 Group
--             HDLC Group
--             Interfaces Group
-- See Annex I for object definitions to be supported.

--5.4.23.7  Synchronous RS-232 Communications Ports
-- To support the synchronous, serial protocol running at 
-- any of the defined communications ports, the object 
-- definitions contained in the following tables within 
-- Annex I shall be supported:
--             SNMP Group
--             System Group
--             RS232 Group
--             HDLC Group
--             Interfaces Group
-- See Annex I for object definitions to be supported.

--5.4.15.3  Port 1 Timeout Fault
port1TimeoutFault OBJECT-TYPE
    SYNTAX Integer32 (0..255)
    MAX-ACCESS read-only
    STATUS deprecated
    DESCRIPTION "<Definition> This object is the number of Port 1 Timeout Faults during the previous 24-hour period. CUs which do not support a Port 1 Timeout Fault shall report a value of 255. A value of 254 shall indicate 254 or more timeouts during the previous 24-hour period.
    <Object Identifier> 1.3.6.1.4.1.1206.4.2.1.3.23.8
    <Object Type> S"
    REFERENCE "NEMA TS 2 Section 4.4.6"
    DEFVAL  { 255 }
    ::= { commPorts 8 }

--5.4.23.9  Serial Bus 1 Fault 
serialBus1Fault OBJECT-TYPE
    SYNTAX Integer32 (0..255)
    MAX-ACCESS read-only
    STATUS deprecated
    DESCRIPTION "<Definition> This object is the number of Serial Bus 1 timeout failures measured during the previous 24 hour period. CUs which do not support a Serial Bus 1 Timeout Failures shall report a value of 255. A value of 254 shall indicate 254 or more timeouts during the previous 24 hour period.
    <Object Identifier> 1.3.6.1.4.1.1206.4.2.1.3.23.9
    <Object Type> S"
    REFERENCE "ATC 5301 Section 9"
    DEFVAL  { 255 }
    ::= { commPorts 9 }

--5.4.24    Maximum Number of OIDs for Global Set ID Parameter
maxGlobalSetIds OBJECT-TYPE
    SYNTAX Integer32 (0..65535)
    MAX-ACCESS read-only
    STATUS deprecated
    DESCRIPTION "<Definition>The maximum number of object identifiers that can be used to create the value of the globalSetIDParameter as supported by this CU.
    <Object Type> S
    <Object Identifier> 1.3.6.1.4.1.1206.4.2.1.3.24"
    ::= { unit 24 }

--5.4.25    Global Set ID Parameter Definition Table
globalSetIdTable OBJECT-TYPE
    SYNTAX SEQUENCE OF GlobalSetIdEntry
    MAX-ACCESS not-accessible
    STATUS deprecated
    DESCRIPTION "<Definition> This table contains the object identifiers used
        to create the globalSetIDParameter. The number of rows within this
        table shall not exceed the value of maxGlobalSetIds.

        If the rows within this table are defined, the OIDs shall be used in
        order, as indicated by the globalSetIdNumber, to create the value of
        the globalSetIDParameter object. The algorithm used to create the
        actual value of the globalSetIDParameter is not defined by this
        standard, but may be a CRC algorithm.

        If there are no rows defined within this table, then the value of the
        globalSetIDParameter object shall be created as defined in NTCIP
        1201v03, Section 2.2.1.
    <TableType> static
    <Object Identifier> 1.3.6.1.4.1.1206.4.2.1.3.25"
    ::= { unit 25 }

globalSetIdEntry OBJECT-TYPE
    SYNTAX GlobalSetIdEntry
    MAX-ACCESS not-accessible
    STATUS deprecated
    DESCRIPTION "<Definition> This object defines a row in the globalSetIdTable.
    <Object Identifier> 1.3.6.1.4.1.1206.4.2.1.3.25.1"
    INDEX { globalSetIdNumber }
    ::= { globalSetIdTable  1 }

GlobalSetIdEntry ::= SEQUENCE {
    globalSetIdNumber Integer32,--deprecated
    globalSetIdOID    OBJECT IDENTIFIER }--deprecated

--5.4.25.1  Global Set ID Number
globalSetIdNumber OBJECT-TYPE
    SYNTAX Integer32 (1..65535)
    MAX-ACCESS not-accessible
    STATUS deprecated
    DESCRIPTION "<Definition> The global ID number for objects in this row. This value shall not exceed maxGlobalSetIds.
    <Object Identifier> 1.3.6.1.4.1.1206.4.2.1.3.25.1.1
    <Object Type> S"
    ::= { globalSetIdEntry 1 }

--5.4.25.2  Global Set ID Object Identifier
globalSetIdOID OBJECT-TYPE
    SYNTAX OBJECT IDENTIFIER
    MAX-ACCESS read-write
    STATUS deprecated
    DESCRIPTION "<Definition> This object contains one of the object identifiers that are to be used to create the value of the globalSetIDParameter. A value of NULL indicates no further object identifiers will be used to determine the globalSetIDParameter (i.e., end of the list of object identifiers).
    <Object Identifier> 1.3.6.1.4.1.1206.4.2.1.3.25.1.2
    <Object Type> P"
    ::= { globalSetIdEntry 2 }

--5.4.26    Unit Alarm Status 3
unitAlarmStatus3 OBJECT-TYPE
    SYNTAX Integer32 (0..255)
    MAX-ACCESS read-only
    STATUS deprecated
    DESCRIPTION "<Definition> Device Alarm Mask 3 ( 0 = False, 1 = True) as
        follows:
        Bit 7: Reserved
        Bit 6: Reserved
        Bit 5: CV Certificate = Whenever the CU detects a fault related to
                invalid connected vehicle certificates.
        Bit 4: Power Issues = Whenever the CU detects power issues such as
                brown-outs or brief black outs but do not lead to a shutdown
                of the CU
        Bit 3: RSU Link Status = Whenever the CU is configured to communicate
                with a RSU but the communications link is failed (e.g.,
                timeouts, errors).
        Bit 2: UPS Link Status = Whenever the CU is configured to communicate
                with a UPS but the communications link is failed (e.g.,
                timeouts, errors).
        Bit 1: CMU Link Status = Whenever the CU is configured to communicate
                with CMU but the communication link is failed (e.g., timeouts,
                errors).
        Bit 0: Communications Timeout = Whenever the CU detects a
                communications timeout on an enabled communications port on
                the ASC.

        Once set, a bit shall maintain its state as long as the condition
        exists.
    <Object Identifier> 1.3.6.1.4.1.1206.4.2.1.3.26
    <Object Type> S"
    ::= { unit 26 }

--5.4.27    Unit Alarm Status 4
unitAlarmStatus4 OBJECT-TYPE
    SYNTAX Integer32 (0..255)
    MAX-ACCESS read-only
    STATUS deprecated
    DESCRIPTION "<Definition> Device Alarm Mask 4 ( 0 = False, 1 = True) as
        follows:
        Bit 7: Reserved
        Bit 6: Reserved
        Bit 5: USB = Whenever the CU detects a USB memory device.
        Bit 4: Scheduler = Whenever the CU is not implementing a scheduled
                pattern or scheduled action.
        Bit 3: Clock = Whenever the CU detects an error with the CU's internal
                clock.
        Bit 2: Cabinet Environmental Sensors = Whenever the cabinet
                environmental conditions measured by the CU exceeds the
                thresholds (e.g., temperature, humidity).
        Bit 1: Preempt Maximum Presence - Preempt maximum presence time
                exceeded
        Bit 0: Memory Fault = Whenever the CU detects a memory fault within
                the controller unit, such as in the firmware, a database or
                RAM.
    <Object Identifier> 1.3.6.1.4.1.1206.4.2.1.3.27
    <Object Type> S"
    ::= { unit 27 }

--5.4.16    Unit Alarm Status 
unitAlarmStatus OBJECT-TYPE
    SYNTAX BITS {  cycleFault(0),
                   coordFault(1),
                   coordFail(2),
                   cycleFail(3),
                   localFree(4),
                   coordActive(5),
                   ioLinkError(6),
                   smuLinkError(7),
                   rsuLinkError(8),
                   cvCertificateError(9),
                   preemmptMaxPresence(10),
                   eclaActive(11)   }
    MAX-ACCESS read-only
    STATUS current
    DESCRIPTION "<Definition> Device Alarm Mask ( 0 = False, 1 = True) as
        follows:
        Bit 0: Cycle Fault - When the CU is operating in the coordinated mode and cycling diagnostics indicate that a serviceable call exists that has not been serviced for two cycles.
        Bit 1: Coord Fault - When a Cycle Fault is in effect and the serviceable call has been serviced within two cycles after the Cycle Fault.
        Bit 2: Coord Fail - When a Coord Fault is in effect and a Cycle Fault occurs again within two cycles of the coordination retry.
        Bit 3: Cycle Fail - When a local CU is operating in the non-coordinated mode, whether the result of a Cycle Fault or Free being the current normal mode, and cycling diagnostics indicate that a serviceable call exists that has not been serviced for two cycles.
        Bit 4: Local Free - When any of the CU inputs and/or programming cause it not to run coordination. The localFreeStatus object indicates why the CU is not running coordination.
        Bit 5: Coordination Active - When coordination is active and not preempted or overridden.
        Bit 6: IO Link Error - When the CU has a communication error with an IO device in the cabinet. 
        Bit 7: SMU Link Error - Whenever the CU is unable to communicate to the signal monitoring unit because the the communication link is failed (e.g., timeouts, errors) or because the signal monitoring unit has been removed.
        Bit 8: RSU Link Error - Whenever the CU is configured to communicate with a RSU but the communications link is failed (e.g., timeouts, errors).
        Bit 9: CV Certificate Error - Whenever the CU detects an error related to invalid connected vehicle certificates.
        Bit 10: Preempt Maximum Presence - Preempt maximum presence time exceeded.
        Bit 11: ECLA Active- The CU is currently being controlled by an External Local Control Application.
    <Object Identifier> 1.3.6.1.4.1.1206.4.2.1.3.28
    <Object Type> S"
    ::= { unit 28 }

--5.4.17  Short Alarm Status
shortAlarmStatusv4 OBJECT-TYPE
    SYNTAX BITS { preemptActive(0),
                flashActive(1),
                transitioning(2),
                localOveride(3),
                coordinationAlarm(4),
                detectorFault(5),
                externalAlarm(6),
                stopTime(7),
                priorityCall(8) }
    MAX-ACCESS read-only
    STATUS current
    DESCRIPTION "<Definition> Short Alarm Mask ( 0 = False, 1 = True) as
        follows:

        Bit 0: Preempt - When any of the CU Preempt inputs become active.
        Bit 1: Flash Active - When the CU is in Flash. The unitFlashStatus object indicates the reason the CU is in flash. 
        Bit 2: Transitioning - Whenever the CU is performing an offset
                transition (correction in process).
        Bit 3: Local Override - When any of the CU inputs and/or programming
                cause it not to run coordination.
        Bit 4: Coordination Alarm - When the CU is not running the called
                pattern without offset correction within three cycles of the
                command. An offset correction requiring less than three cycles
                due to cycle overrun caused by servicing a pedestrian call
                shall not cause a Coordination Alarm.
        Bit 5: Detector Fault - When any vehicle or pedestrian detector fault occurs.
        Bit 6: External Alarm - When a user configured alarm input is active. The alarmGroupTable indicates which alarm input is active. 
        Bit 7: Stop Time - When the Stop Time input is active.
        Bit 8: Priority Call - The CU is currently responding to a Priority Call using NTCIP 1211 or another method. 
    <Object Identifier> 1.3.6.1.4.1.1206.4.2.1.3.29
    <Object Type> S"
    ::= { unit 29 }

--5.4.18 Unit Control
unitControlV4 OBJECT-TYPE
    SYNTAX BITS { disableRemoteCommand(0),
                manualBackup(1),
                globalMinRecall(2),
                nonactuated1(3),
                nonactuated2(4),
                walkRestModifier(5),
                interconnect(6) }
    MAX-ACCESS read-write
    STATUS current
    DESCRIPTION "<Definition> This object is used to allow a remote entity to
        activate unit functions in the device (0 = False / Disabled, 1 = True
        / Enabled) as follows:

        Bit 0: Disable Remote Commands - when set to 1, causes the CU to ignore
                commands (all SET requests) from all management station except
                and until this bit is SET to 0 (i.e., a management station can
                still SET this bit to 0 to enable Remote Command).
        Bit 1: Manual Backup - when set to 1, causes the CU to go into BACKUP Mode regardless of the BACKUP timer. The value of this object will clear when this bit is set.
        Bit 2: Global Minimum Recall - when set to 1, causes a recurring
                demand on all vehicle phases for a minimum vehicle service.
                REFERENCE NEMA TS 2 Clause 3.5.5.5.9
        Bit 3: Call to Non-Actuated 1 - when set to 1, causes any phase(s)
                appropriately programmed in the phaseOptions object to operate
                in the Non-Actuated Mode.
                REFERENCE NEMA TS 2 Clause 3.5.5.5.8
        Bit 4: Call to Non-Actuated 2 - when set to 1, causes any phase(s)
                appropriately programmed in the phaseOptions object to operate
                in the Non-Actuated Mode.
                REFERENCE NEMA TS 2 Clause 3.5.5.5.8
        Bit 5: Walk Rest Modifier - when set to 1, causes non-actuated phases
                to remain in the timed-out Walk state (rest in Walk) in the
                absence of a serviceable conflicting call.
                REFERENCE NEMA TS 2 Clause 3.5.5.5.13
        Bit 6: Interconnect - when set to 1, shall cause the interconnect
                inputs to operate at a higher priority than the timebase
                control (TBC On Line).
                REFERENCE NEMA TS 2 Clause 3.6.2.3 and 3.8.3
        
    The device shall reset this object to ZERO when in BACKUP Mode. A write to this object shall reset the BACKUP timer (see unitBackupTime).
    <Object Identifier> 1.3.6.1.4.1.1206.4.2.1.3.30
    <Object Type> C"
    ::= { unit 30 }

--5.5   Coordination Parameters
coord OBJECT IDENTIFIER
    ::= { asc 4 }

-- The coord node contains objects that support coordination configuration, status and control functions for the device.

--5.5.1 Coordination Operational Mode Parameter
coordOperationalMode OBJECT-TYPE
    SYNTAX Integer32 (0..255)
    MAX-ACCESS read-write
    STATUS current
    DESCRIPTION "<Definition> This object defines the operational mode for
        coordination. The possible modes are:

        Value   DESCRIPTION
        0       Automatic - this mode provides for coord operation, free,
                    and flash to be determined automatically by the possible
                    sources (i.e. Interconnect, Time Base, or System Commands).
        1-253   Manual Pattern - these modes provide for Coord operation
                    running this pattern. This selection of pattern overrides
                    all other pattern commands.
        254     Manual Free - this mode provides for Free operation without
                    coordination or Automatic Flash from any source.
        255     Manual Flash - this mode provides for Automatic Flash without
                    coordination or Free from any source.
    <Object Identifier> 1.3.6.1.4.1.1206.4.2.1.4.1
    <Object Type> P"
    REFERENCE "NEMA TS 2 Clause 3.6.2.4"
    ::= { coord 1 }

--5.5.2 Coordination Correction Mode Parameter
coordCorrectionMode OBJECT-TYPE
    SYNTAX INTEGER { other (1),
                     dwell (2),
                     shortway (3),
                     addOnly (4),
                     subtractOnly (5) }
    MAX-ACCESS read-write
    STATUS current
    DESCRIPTION "<Definition> This object defines the Coordination Correction Mode.
        The possible modes are:
        other: the coordinator establishes a new offset by a mechanism not
            defined in this standard.
        dwell: when changing offset, the coordinator shall establish a new
            offset by dwelling in the coord phase(s) until the desired offset
            is reached.
        shortway (Smooth): when changing offset, the coordinator shall
            establish a new offset by adding or subtracting to/from the
            timings in a manner that limits the cycle change. This operation
            is performed in a device specific manner.
        addOnly: when changing offset, the coordinator shall establish a new
            offset by adding to the timings in a manner that limits the cycle
            change. This operation is performed in a device specific manner.
        subtractOnly: when changing offset, the coordinator shall establish a
            new offset by subtracting from the timings in a manner that limits
            the cycle change. This operation is performed in a device specific
            manner.
    <Object Identifier> 1.3.6.1.4.1.1206.4.2.1.4.2
    <Object Type> P"
    DEFVAL { 3 }
    ::= { coord 2 }

--5.5.3 Coordination Maximum Mode Parameter
coordMaximumMode OBJECT-TYPE
    SYNTAX INTEGER { other (1),
                     maximum1 (2),
                     maximum2 (3),
                     maxInhibit (4),
                     maximum3 (5) }
    MAX-ACCESS read-write
    STATUS current
    DESCRIPTION "This object defines the Coordination Maximum Mode. The possible
        modes are:
        other: the maximum mode is determined by some other mechanism not
            defined in this standard.
        maximum1: the internal Maximum 1 Timing shall be effective while
            coordination is running a pattern. 
        maximum2: the internal Maximum 2 Timing shall be effective while
            coordination is running a pattern. 
        maxInhibit: the internal Maximum Timing shall be inhibited while
            coordination is running a pattern.
        maximum3: the internal Maximum 3 Timing shall be effective while
            coordination is running a pattern.
    <Object Identifier> 1.3.6.1.4.1.1206.4.2.1.4.3
    <Object Type> P"
    DEFVAL { 4 }
    ::= { coord 3 }

--5.5.4 Coordination Force Mode Parameter
unitCoordForceMode OBJECT-TYPE
    SYNTAX INTEGER { other(1),
                     floating (2),
                     fixed (3) }
    MAX-ACCESS read-write
    STATUS current
    DESCRIPTION "<Definition> This object defines the Unit Force Mode. The
        possible modes are:
        other: the CU implements a mechanism not defined in this standard.
        floating: each non-coord phase will be forced to limit its time to the
            split time value. This allows unused split time to revert to the
            coord phase.
        fixed: each non-coord phase will be forced at a fixed position in the
            cycle. This allows unused split time to revert to the following
             phase.
    This does not apply to phases operating with Max Vehicle Recall, a nonactuated split mode, or a Call to Nonactuated input. 
    This object was named coordForceMode in 1202 v03.
    <Object Identifier> 1.3.6.1.4.1.1206.4.2.1.4.4
    <Object Type> P"
    DEFVAL { 3 }
    ::= { coord 4 }

--5.5.5 Maximum Patterns
maxPatterns OBJECT-TYPE
    SYNTAX Integer32 (1..253)
    UNITS   "patterns"
    MAX-ACCESS read-only
    STATUS current
    DESCRIPTION "<Definition> The maximum number of Patterns this Controller Unit supports. This object indicates how many rows are in the patternTable object (254 and 255 are defined as non-pattern Status for Free and Flash).
    <Object Identifier> 1.3.6.1.4.1.1206.4.2.1.4.5
    <Object Type> S"
    ::= { coord 5 }

--5.5.6 Pattern Table Type
patternTableType OBJECT-TYPE
    SYNTAX INTEGER { other (1),
                     patterns (2),
                     offset3 (3),
                     offset5 (4) }
    MAX-ACCESS read-only
    STATUS deprecated
    DESCRIPTION "<Definition> This object provides information about any special organizational structure required for the pattern table. The defined structures are as follows:
other: The pattern table setup is not described in this standard, refer to device manual.
patterns: Each row of the pattern table represents a unique pattern and has no dependencies on other rows.
offset3: The pattern table is organized into plans which have three offsets. Each plan uses three consecutive rows. Only patternOffsetTime and patternSequenceNumber values may vary between each of the three rows. Plan 1 is contained in rows 1, 2 and 3, Plan 2 is contained in rows 4, 5 and 6, Plan 3 is in rows 7, 8 and 9, etc.
offset5:  The pattern table is organized into plans which have five offsets. Each plan occupies five consecutive rows. Only patternOffsetTime and patternSequenceNumber values may vary between each of the rows. Plan 1 is contained in rows 1, 2, 3, 4 and 5, Plan 2 is contained in rows 6, 7, 8, 9 and 10, Plan 3 is contained in rows 11, 12, 13, 14 and 15, etc.
    <Object Identifier> 1.3.6.1.4.1.1206.4.2.1.4.6
    <Object Type> S"
    REFERENCE "NEMA TS 2 Clause 3.6.2.1 and 3.6.2.2"
    ::= { coord 6 }

--5.5.6 Pattern Table
patternTable OBJECT-TYPE
    SYNTAX SEQUENCE OF PatternEntry
    MAX-ACCESS not-accessible
    STATUS current
    DESCRIPTION "<Definition> A table containing Actuated Controller Unit coordination Pattern parameters. The number of rows in this table is equal to the maxPatterns object.

    <TableType> static
    <Object Identifier> 1.3.6.1.4.1.1206.4.2.1.4.7"
    ::= { coord 7 }

patternEntry OBJECT-TYPE
    SYNTAX PatternEntry
    MAX-ACCESS not-accessible
    STATUS current
    DESCRIPTION "<Definition> Parameters for a specific Actuated Controller Unit pattern.
    <Object Identifier> 1.3.6.1.4.1.1206.4.2.1.4.7.1"
    INDEX   { patternNumber }
    ::= { patternTable 1 }

PatternEntry ::= SEQUENCE {
    patternNumber                   Integer32,
    patternCycleTime                Integer32,
    patternOffsetTime               Integer32,
    patternSplitNumber              Integer32,
    patternSequenceNumber           Integer32,
    patternCoordSyncPoint           INTEGER,--deprecated
    patternMaximumMode              INTEGER, 
    patternSpatEnabledLanes         Integer32, 
    patternReferencePhase           Integer32,
    patternReferencePoint           INTEGER,
    patternPhaseSet                 Integer32,
    patternOverlapSet               Integer32,
    patternVehicleDetectorSet       Integer32,
    patternPedestrianDetectorSet    Integer32,
    patternSpecialFunction          Unsigned32,
    patternStatus                   BITS   } 

--5.5.6.1   Pattern Number
patternNumber OBJECT-TYPE
    SYNTAX Integer32 (1..253)
    UNITS   "pattern"
    MAX-ACCESS not-accessible
    STATUS current
    DESCRIPTION "<Definition> The pattern number for objects in this row. This
        value shall not exceed the maxPatterns object value. This value may be referenced by ISO 26048-1. 
    <Object Identifier> 1.3.6.1.4.1.1206.4.2.1.4.7.1.1"
    ::= { patternEntry 1 }

--5.5.6.2   Pattern Cycle Time Parameter
patternCycleTime OBJECT-TYPE
    SYNTAX Integer32 (0..999)
    UNITS "second"
    MAX-ACCESS read-write
    STATUS current
    DESCRIPTION "<Definition> The patternCycleTime object specifies the length
        of the pattern cycle in seconds (NEMA TS 2 range: 30-255). A value of zero
        is used for a pattern where the ASC runs in Free mode. Otherwise, the
        pattern is configured for coordination, 
    
        A pattern cycle time less than adequate to service the minimum
        requirements of all phases shall result in Free mode. While this
        condition exists, the Local Free bit of unitAlarmStatus shall be 1, the
        Local Override bit of shortAlarmStatusv4 shall be 1, the value
        localFreeStatus shall be badPlan(7), and the Bad Cycle Time bit of
        patternStatus shall be 1. 

        The minimum time to serve a phase must satisfy vehicle minimum green,
        walk (if configured), pedestrian clear (if configured), yellow change,
        and red clearance time. 

        If the pattern cycle time is zero and the associated split table (if
        any) contains values greater than zero, then the ASC shall utilize the
        split time values as maximum values for each phase.
    <Object Identifier> 1.3.6.1.4.1.1206.4.2.1.4.7.1.2
    <Object Type> P"
    REFERENCE "NEMA TS 2 Clause 3.6.2.1.1"
    DEFVAL { 0 }
    ::= { patternEntry 2 }
 
--5.5.6.3   Pattern Offset Time Parameter
patternOffsetTime OBJECT-TYPE
    SYNTAX Integer32 (0..998)
    UNITS "second"
    MAX-ACCESS read-write
    STATUS current
    DESCRIPTION "<Definition> The patternOffsetTime defines by how many seconds
        (NEMA TS 2 range: 0-254) the local time zero shall lag the system time
        zero (synchronization pulse) for this pattern. 
    
        An offset value equal to or greater than the patternCycleTime other
        than 0 shall result in the ASC running in Free mode. While this
        condition exists, the Local Free bit of unitAlarmStatus shall be 1, the
        Local Override bit of shortAlarmStatusv4 shall be 1, the value of
        localFreeStatus shall be badPlan(7), and the Invalid Offset bit of
        patternStatus for this pattern shall be 1. 

        The value of this object is ignored when patternCycleTime is 0. 
    <Object Identifier> 1.3.6.1.4.1.1206.4.2.1.4.7.1.3
    <Object Type> P"
    REFERENCE "NEMA TS 2 Clause 3.6.2.2"
    DEFVAL { 0 }
    ::= { patternEntry 3 }

--5.5.6.4   Pattern Split Number Parameter
patternSplitNumber OBJECT-TYPE
    SYNTAX Integer32 (0..255)
    UNITS   "split"
    MAX-ACCESS read-write
    STATUS current
    DESCRIPTION "<Definition> This object is used to locate information in the splitTable to use for this pattern. This value shall not exceed the maxSplits object value. A value of zero is used for a pattern where the ASC runs in Free mode.
    <Object Identifier> 1.3.6.1.4.1.1206.4.2.1.4.7.1.4
    <Object Type> P"
    DEFVAL { 0 }
    ::= { patternEntry 4 }

--5.5.6.5   Pattern Sequence Number Parameter
patternSequenceNumber OBJECT-TYPE
    SYNTAX Integer32 (0..255)
    UNITS "sequence"
    MAX-ACCESS read-write
    STATUS current
    DESCRIPTION "<Definition> This object is used to locate information in the sequenceTable to use with this pattern. This value shall not exceed the maxSequences object value. A value of zero indicates no sequence is specified and Automatic Flash without coordination is to run when this pattern is called.
    <Object Identifier> 1.3.6.1.4.1.1206.4.2.1.4.7.1.5
    <Object Type> P"
    DEFVAL { 1 }
    ::= { patternEntry 5 }

--5.5.7.6	Pattern Coordination Sync Point
patternCoordSyncPoint OBJECT-TYPE
SYNTAX INTEGER { other (1),
	unitCoordSyncPoint (2),
    firstCoordPhsGrnBegin (3),
    lastCoordPhsGrnBegin (4),
    firstCoordPhsGrnEnd (5),
    lastCoordPhsGrnEnd (6),
    firstCoordPhsYelEnd (7),
    lastCoordPhsYelEnd (8) }
    MAX-ACCESS read-write
    STATUS deprecated
    DESCRIPTION "<Definition> This object is used to indicate the location of the system reference point for this pattern. The valid coordination sync points are:
other: the coordination sync point is not described in this standard
unitCoordSyncPoint: the coordination point is defined by unitCoordSyncPoint.
firstCoordPhsGrnBegin: the coordination point is the beginning of the Green indication of the first coordinated phase.
lastCoordPhsGrnBegin: the coordination point is the beginning of the Green indication of the last coordinated phase.
firstCoordPhsGrnEnd: the coordination point is end of the green indication of the first coordinated phase.
lastCoordPhsGrnEnd: the coordination point is the end of the green indication of the last coordinated phase.
firstCoordPhsYelEnd: the coordination point is the end of the yellow indication of the first coordinated phase.
lastCoordPhsYelEnd: the coordination point is the end of the yellow indication of the last coordinated phase.
<Object Identifier> 1.3.6.1.4.1.1206.4.2.1.4.7.1.6
<Object Type> P"
DEFVAL { 3 }
::= { patternEntry 6 }

--5.5.6.6   Pattern Maximum Mode Parameter
patternMaximumMode OBJECT-TYPE
    SYNTAX INTEGER { other (1),
        coordMaximumMode (2),
        maxInhibit (3),
        maximum1 (4),
        maximum2 (5),
        maximum3 (6) }
    MAX-ACCESS read-write
    STATUS current
    DESCRIPTION "<Definition> This object represents the maximum mode to be used for the pattern. The valid maximum modes are:
other: the maximum mode is determined by some other mechanism not defined in this standard.
coordMaximumMode: use the maximum mode defined by the coordMaximumMode object.
maxInhibit: the internal maximum timing shall be inhibited while coordination is running this pattern.
maximum1: the internal Maximum 1 Timing shall be effective while coordination is running this pattern.
maximum2: the internal Maximum 2 Timing shall be effective while coordination is running this pattern.
maximum3: the internal Maximum 3 Timing shall be effective while coordination is running this pattern.

This object was named patternOptions in 1202 v03. 
    <Object Identifier> 1.3.6.1.4.1.1206.4.2.1.4.7.1.7
    <Object Type> P"
    DEFVAL { 2 }
    ::= { patternEntry 7 }

--5.5.6.7  Pattern Enabled Lanes
patternSpatEnabledLanes OBJECT-TYPE
    SYNTAX Integer32 (0..255)
    MAX-ACCESS read-write
    STATUS current
    DESCRIPTION "<Definition> This value is equal to the enabledLaneIndex
        (row) in the spatEnabledLanesConcurrencyTable that contains the
        enabledLaneConcurrency lanes to be active when this pattern is active.
        A value of zero indicates that no revocable lanes are to be enabled as part
        of this pattern. Any lane that is not revocable remains active. This value shall not exceed maxPatterns.
    <Object Identifier> 1.3.6.1.4.1.1206.4.2.1.4.7.1.8
    <Object Type> P"
    DEFVAL { 0 }
    ::= { patternEntry 8 }

--5.5.6.8   Pattern Reference Phase Parameter
patternReferencePhase OBJECT-TYPE
    SYNTAX Integer32 (0..255)
    UNITS "phase"
    MAX-ACCESS read-write
    STATUS current
    DESCRIPTION "<Definition> This object is used to identify the phase that contains the reference point for when the pattern cycle starts and ends. This value shall not exceed maxPhases. This phase is must be coordinated phase if the pattern is used for coordination. The reference point is identified by patternReferencePoint. A value of zero is used for a pattern where the ASC runs in Free mode.

    If the selected phase is not in the sequence identified in patternSequenceNumber or if this phase is not a coordinated phase as specified in associated split table (if any), the device shall operate in Free Mode. While this condition exists, the Local Free bit of unitAlarmStatus shall be 1, the Local Override bit of shortAlarmStatusv4 shall be 1, the value of localFreeStatus is badPlan(7), and the Invalid Reference Point bit of patternStatus is 1. 

    The value of this object is ignored when patternCycleTime is 0. 

    <Object Identifier> 1.3.6.1.4.1.1206.4.2.1.4.7.1.9
    <Object Type> P"
    DEFVAL { 0 }
    ::= { patternEntry 9 }

--5.5.6.9   Pattern Reference Point Parameter
patternReferencePoint OBJECT-TYPE
    SYNTAX INTEGER { other(1),
                    greenBegin (2),
                    yellowBegin (3),
                    redBegin (4),
                    redEnd (5) }
    MAX-ACCESS read-write
    STATUS current
    DESCRIPTION "<Definition> This object is used to indicate the location of the reference point for when the pattern cycle starts and ends. This object identifies an interval within the phase identified by the patternReferencePhase. The valid values are:

    other: The reference point is a position not defined by this object. 
    greenBegin: The start of the vehicle GREEN interval. If phasePedAdvanceWalkTime is used, then this is the start of the walk interval.
    yellowBegin: The start of the yellow change interval.
    redBegin: The start of the red clearance interval.
    redEnd: The end of the red clearance interval.

    The value of this object is ignored when patternCycleTime is 0. 
    
    <Object Identifier> 1.3.6.1.4.1.1206.4.2.1.4.7.1.10
    <Object Type> P"
    ::= { patternEntry 10 }

--5.5.6.10   Pattern Phase Set Number Parameter
patternPhaseSet OBJECT-TYPE
    SYNTAX Integer32 (1..255)
    UNITS "set"
    MAX-ACCESS read-write
    STATUS current
    DESCRIPTION "<Definition> This object is used to identify the phase set to be used with this pattern. This value shall not exceed the maxPhaseSets object value. 
    <Object Identifier> 1.3.6.1.4.1.1206.4.2.1.4.7.1.11
    <Object Type> P"
    DEFVAL { 1 }
    ::= { patternEntry 11 }

--5.5.6.11  Pattern Overlap Set Number Parameter
patternOverlapSet OBJECT-TYPE
    SYNTAX Integer32 (1..255)
    UNITS "set"
    MAX-ACCESS read-write
    STATUS current
    DESCRIPTION "<Definition> This object is used to identify the overlap set to be used with this pattern. This value shall not exceed the maxOverlapSets object value.
    <Object Identifier> 1.3.6.1.4.1.1206.4.2.1.4.7.1.12
    <Object Type> P"
    DEFVAL { 1 }
    ::= { patternEntry 12 }

--5.5.6.12  Pattern Vehicle Detector Set Number Parameter
patternVehicleDetectorSet OBJECT-TYPE
    SYNTAX Integer32 (1..255)
    UNITS "set"
    MAX-ACCESS read-write
    STATUS current
    DESCRIPTION "<Definition> This object is used to identify the vehicle detector set to be used with this pattern. This value shall not exceed the maxVehicleDetectorSets object value.
    <Object Identifier> 1.3.6.1.4.1.1206.4.2.1.4.7.1.13
    <Object Type> P"
    DEFVAL { 1 }
    ::= { patternEntry 13 }

--5.5.6.13  Pattern Pedestrian Detector Set Number Parameter
patternPedestrianDetectorSet OBJECT-TYPE
    SYNTAX Integer32 (1..255)
    UNITS "set"
    MAX-ACCESS read-write
    STATUS current
    DESCRIPTION "<Definition> This object is used to identify the vehicle detector set to be used with this pattern. This value shall not exceed the maxVehicleDetectorSets object value.
    <Object Identifier> 1.3.6.1.4.1.1206.4.2.1.4.7.1.14
    <Object Type> P"
    DEFVAL { 1 }
    ::= { patternEntry 14 }

--5.5.6.14  Pattern Special Functions Parameter
patternSpecialFunction OBJECT-TYPE
    SYNTAX Unsigned32 (0..4294967295)
    MAX-ACCESS read-write
    STATUS current
    DESCRIPTION "<Definition> The Special Functions that shall be active when this pattern is active. Each bit represents a special function # from 1 to 32. 
        Bit 31: Special Function 32
        Bit 30: Special Function 31
        Bit 29: Special Function 30
        .... .... .... ....
        Bit 3: Special Function 4
        Bit 2: Special Function 3
        Bit 1: Special Function 2
        Bit 0: Special Function 1

        Bit = 0 - False/Disabled, Bit = 1 - True/Enabled

        If the ASC supports less than 32 special functions, a SET of a bit for an unsupported special function shall return a badValue(3) error.
    <Object Identifier> 1.3.6.1.4.1.1206.4.2.1.4.7.1.15
    <Object Type> P"
     DEFVAL { 0 }
    ::= { patternEntry 15 }

--5.5.6.15  Pattern Status
patternStatus OBJECT-TYPE
    SYNTAX BITS { running(0),
                badCycleTime(1),
                splitOverun(2),
                invalidOffset(3),
                invalidReferencePoint(4) }
    MAX-ACCESS read-only
    STATUS current
    DESCRIPTION "<Definition> This object indicates whether this pattern is running or why the pattern is invalid.

        Bit 0: Running - The CU is currently running this pattern and there is no issue with this pattern.
        Bit 1: Bad Cycle Time - The pattern cycle time is not adequate to service the minimum requirements of all phases, except when patternCycleTime is 0. The minimum time to serve a phase must satisfy vehicle minimum green, walk (if configured), pedestrian clear (if configured), yellow change, and red clearance time. 
        Bit 2: Split Overrun - The sum of all split times exceeds the programmed patternCycleTime value.
        Bit 3: Invalid Offset - The programmed pattern offset time value is not less than the programmed cycle time value, except when patternCycleTime is 0.
        Bit 4: Invalid Reference Point - If the pattern is configured for coordination (patternCycleTime is greater than 0), the pattern reference point is invalid if the patternReferencePhase is not a coordinated phase as defined by splitCoordPhase in the associated split group or not in the pattern sequence as defined in the sequenceData of the associated sequence. 
        
    <Object Identifier> 1.3.6.1.4.1.1206.4.2.1.4.7.1.16
    <Object Type> S"
    ::= { patternEntry 16 }

--5.5.7 Maximum Splits
maxSplits OBJECT-TYPE
    SYNTAX Integer32 (1..255)
    UNITS   "split"
    MAX-ACCESS read-only
    STATUS current
    DESCRIPTION "<Definition> The maximum number of Split Plans this Actuated Controller Unit supports. This object indicates how many Split plans are in the splitTable object.
    <Object Identifier> 1.3.6.1.4.1.1206.4.2.1.4.8
    <Object Type> S"
    ::= { coord 8 }

--5.5.8 Split Table
splitTable OBJECT-TYPE
    SYNTAX SEQUENCE OF SplitEntry
    MAX-ACCESS not-accessible
    STATUS current
    DESCRIPTION "<Definition> A table containing Actuated Controller Unit coordination split parameters. The number of rows in this table is equal to maxSplits.
    <TableType> static
    <Object Identifier> 1.3.6.1.4.1.1206.4.2.1.4.9"
    ::= { coord 9 }

splitEntry OBJECT-TYPE
    SYNTAX SplitEntry
    MAX-ACCESS not-accessible
    STATUS current
    DESCRIPTION "<Definition> Split type Parameters for a specific  Actuated Controller Unit phase.
    <Object Identifier> 1.3.6.1.4.1.1206.4.2.1.4.9.1"
    INDEX   { splitNumber, splitPhase }
    ::= { splitTable 1 }

SplitEntry ::= SEQUENCE {
    splitNumber         Integer32,
    splitPhase          Integer32,
    splitTime           Integer32,
    splitMode           INTEGER,
    splitCoordPhase     INTEGER,
    splitOptions        Integer32,
    splitCoordForceMode INTEGER}

--5.5.8.1   Split Number
splitNumber OBJECT-TYPE
    SYNTAX Integer32 (1..255)
    UNITS   "split"
    MAX-ACCESS not-accessible
    STATUS current
    DESCRIPTION "<Definition> The object defines which rows of the split table comprise a split group. All rows that have the same splitNumber are in the same split group. The value of this object shall not exceed the maxSplits object value.
    <Object Identifier> 1.3.6.1.4.1.1206.4.2.1.4.9.1.1"
    ::= { splitEntry 1 }

--5.5.8.2   Split Phase Number
splitPhase OBJECT-TYPE
    SYNTAX Integer32 (1..255)
    UNITS "phase"
    MAX-ACCESS not-accessible
    STATUS current
    DESCRIPTION "<Definition> The phase number for objects in this row. The value of this object shall not exceed the maxPhases object value.
    <Object Identifier> 1.3.6.1.4.1.1206.4.2.1.4.9.1.2"
    ::= { splitEntry 2 }

--5.5.8.3   Split Time Parameter
splitTime OBJECT-TYPE
    SYNTAX Integer32 (0..999)
    UNITS "second"
    MAX-ACCESS read-write
    STATUS current
    DESCRIPTION "<Definition> The time in seconds the splitPhase is allowed to receive (i.e. before a Force Off is applied) when constant demands exist on all phases. In floating force mode for coordination this is always the maximum time a non-coordinated phase is allowed to receive. In fixed force mode for coordination, the actual allowed time may be longer if a previous phase gapped out.

    The splitTime includes all phase clearance times for the associated phase. The split time shall at minimum the sum of the phase minimum service requirements for the phase. When the time is NOT adequate to service the minimum service requirements of the phase, the ASC shall operate in Free Mode. 
  
    The minimum time to serve a phase must satisfy vehicle minimum green, walk (if configured), pedestrian clear (if configured), yellow change, and red clearance time. 

    If the patternCycleTime entry of the associated patternTable entry is zero (i.e. the device is in Free Mode), then the value of this object shall be applied, if non-zero, as a maximum time for the associated phase.

    If the sum of all splitTime values for this split group is less than the patternCycleTime entry of the associated patternTable entry, all extra time is allotted to the coordinated phase in each ring.

    If the sum of all splitTime values for this split group is greater than the patternCycleTime entry of the associated patternTable entry (and the patternCycleTime is not zero) the device shall operate in the Free Mode. While this condition exists, the splitOverrun bit of patternStatus of the associated patternTable entry is 1. 

    While the Free Mode condition exists, the Local Free bit of unitAlarmStatus shall be 1, the Local Override bit of shortAlarmStatusv4 shall be 1, and the value of localFreeStatus is badPlan(7).

    <Object Identifier> 1.3.6.1.4.1.1206.4.2.1.4.9.1.3 
    <Object Type> P"
    REFERENCE "NEMA TS 2 Clause 3.6.2.1.2"
    ::= { splitEntry 3 }

--5.5.8.4   Split Mode Parameter
splitMode OBJECT-TYPE
    SYNTAX INTEGER { other(1),
        none (2),
        minimumVehicleRecall (3),
        maximumVehicleRecall (4),
        pedestrianRecall (5),
        maximumVehicleAndPedestrianRecall (6),
        phaseOmitted (7),
        nonActuated (8) }
    MAX-ACCESS read-write
    STATUS current
    DESCRIPTION "<Definition> This object defines operational characteristics of the phase. The following options are available:
other: the operation is not specified in this standard
none: no split mode control.
minimumVehicleRecall: this phase operates with a minimum vehicle recall.
maximumVehicleRecall: this phase operates with a maximum vehicle recall. This value shall also be used for bicycle phase recalls and transit phase recalls.
pedestrianRecall: this phase operates with a pedestrian recall. The settings for minimumVehicleRecall also apply.
maximumVehicleAndPedestrianRecall: this phase operates with a maximum vehicle & pedestrian recall.
phaseOmitted: this phase is omitted.
nonActuated: this phase operates with a fixed split time.
    <Object Identifier> 1.3.6.1.4.1.1206.4.2.1.4.9.1.4
    <Object Type> P"
     DEFVAL { 2 }
    ::= { splitEntry 4 }

--5.5.8.5   Split Coordinated Phase
splitCoordPhase OBJECT-TYPE 
    SYNTAX Integer32 (0..1)
    MAX-ACCESS read-write
    STATUS current
    DESCRIPTION "<Definition> To select the associated phase as a coordinated phase this object shall be set to TRUE (non zero).
    <Object Identifier> 1.3.6.1.4.1.1206.4.2.1.4.9.1.5"
    ::= { splitEntry 5 }

--5.5.8.6   Split Options
splitOptions OBJECT-TYPE
    SYNTAX Integer32 (0..255)
    MAX-ACCESS read-write
    STATUS current
    DESCRIPTION "<Definition> Optional split functions (0 = False/Disabled, 1 = True/Enabled).
Bit 7: Reserved
Bit 6: Reserved
Bit 5: Reserved
Bit 4: Reserved
Bit 3: Reserved
Bit 2: Reserved
Bit 1: Reserved
Bit 0: Transition Phase Omit - To allow the associated phase to be omitted during coord Correction Mode (transitions), this object shall be set to TRUE (1). If the associated phase is not allowed to be omitted, this object shall be set to FALSE (0).

A SET of a 'reserved' bit to a value other than zero (0) shall return a badValue(3) error.

    <Object Identifier> 1.3.6.1.4.1.1206.4.2.1.4.9.1.6
    <Object Type> P"
    ::= { splitEntry 6 }

--5.5.8.7 Split Phase Coord Force Mode Parameter
splitCoordForceMode OBJECT-TYPE
    SYNTAX INTEGER { other(1),
                     unitCoordForceMode(2),
                     floating (3),
                     fixed (4) }
    MAX-ACCESS read-write
    STATUS current
    DESCRIPTION "<Definition> This object defines the Force Mode for the phase when the split is in use. The possible modes are:
        other: the CU implements a mechanism not defined in this standard or this object is not applicable. 
        unitCoordForceMode: The CU uses the current setting of the unitCoordForceMode object for this phase. 
        floating: The phase will be forced to limit its time to the splitTime value.
        fixed: The phase will be forced off at a fixed position in the cycle, allowing its on-time to exceed the splitTime value

    The value of this object for this phase is not used when splitCoordPhase is equal to '1' or if the splitMode is nonActuated.

    <Object Identifier> 1.3.6.1.4.1.1206.4.2.1.4.9.1.7
    <Object Type> P"
     DEFVAL { 2 }
    ::= { splitEntry 7}

--5.5.9    Coordination Pattern Status 
coordPatternStatus OBJECT-TYPE
    SYNTAX Integer32 (1..255)
    MAX-ACCESS read-only
    STATUS current
    DESCRIPTION "<Definition> This object defines the running coordination pattern/mode in the device. The possible values are:
    Value   Description
    1-253   Pattern - indicates the currently running pattern
    254 Manual Free - indicates Manual Free operation without coordination. 
    255 Manual Flash - indicates Manual Flash without coordination.
    <Object Identifier> 1.3.6.1.4.1.1206.4.2.1.4.10
    <Object Type> S"
    ::= { coord 10 }
 
--5.5.10    Local Free Status
localFreeStatus OBJECT-TYPE
    SYNTAX INTEGER { other(1),
    notFree(2),
    commandFree(3),
    transitionFree(4),
    inputFree(5),
    coordFree(6),
    badPlan(7),
    badCycleTime(8),--Deprecated
    splitOverrun (9),--Deprecated
    invalidOffset (10),--Deprecated
    failed(11) }
    MAX-ACCESS read-only
    STATUS current
    DESCRIPTION "<Definition> The Free modes:
    other: some other condition has caused the device to run in free mode.
    notFree: the unit is not running in free mode.
    commandFree: the CU is running Free because there is no pattern command.
    transitionFree: the CU has a pattern command but is cycling to a point to begin coordination.
    inputFree: one of the CU inputs cause it to not respond to coordination.
    coordFree: the CU is programmed to run Free. 
    badPlan: The CU is running Free because the called pattern is invalid. The patternStatus object for the pattern indicates why the called pattern is invalid.
    failed: cycling diagnostics have called for Free.

An ASC may provide diagnostics beyond those stated herein. Therefore, for a set of given bad data, the free status between devices may be inconsistent.
    <Object Identifier> 1.3.6.1.4.1.1206.4.2.1.4.11
    <Object Type> S"
    ::= { coord 11 }

--5.5.11   Coordination Cycle Status
coordCycleStatus OBJECT-TYPE
    SYNTAX Integer32 (0..65535)
    UNITS "second"
    MAX-ACCESS read-only
    STATUS current
    DESCRIPTION "<Definition> The Coord Cycle Status represents the current position 
    in the local coord cycle of the running pattern (0 to 1898 sec). This value normally 
    counts down from patternCycleTime to zero. This value may exceed the patternCycleTime 
    during a coord cycle with offset correction (patternCycleTime + correction).

    Values 1899-65534 are not used. A value of 65535 indicates that the controller is not in coordination because it is running Free or in preemption.  
    
    <Object Identifier> 1.3.6.1.4.1.1206.4.2.1.4.12
    <Object Type> S"
    ::= { coord 12 }

--5.5.12    Coordination Sync Status
coordSyncStatus OBJECT-TYPE
    SYNTAX Integer32 (0..65535)
    UNITS "second"
    MAX-ACCESS read-only
    STATUS current
    DESCRIPTION "<Definition> The Coord Sync Status represents the current time into the master cycle since
        the system reference point for the running pattern (0 to 1898 sec).
        This value normally counts up from zero to the next system reference
        point (patternCycleTime). This value may exceed the patternCycleTime
        during a coord cycle in which the system reference point has changed.

        Values 1899-65534 are not used. A value of 65535 indicates that the controller is not in coordination because it is running Free or in preemption. 
        
    <Object Identifier> 1.3.6.1.4.1.1206.4.2.1.4.13
    <Object Type> S"
    ::= { coord 13 }

--5.5.13    System Pattern Control
systemPatternControl OBJECT-TYPE
    SYNTAX Integer32 (0..255)
    MAX-ACCESS read-write
    STATUS current
    DESCRIPTION "<Definition> This object is used to establish the Called
        System Pattern/Mode for the device. The possible values are:

        Value   DESCRIPTION
        0       Standby - the system relinquishes control of the device.
        1-253   Pattern - these values indicate the system commanded pattern
        254     Free - this value indicates a call for Manual Free
        255     Flash - this value indicates a call for Manual Flash

        If an unsupported / invalid pattern is called, Free shall be the
        operational mode. The device shall reset this object to ZERO when in
        BACKUP Mode. A write to this object shall reset the Backup timer to
        ZERO (see unitBackupTime).
    <Object Identifier> 1.3.6.1.4.1.1206.4.2.1.4.14
    <Object Type> C"
    DEFVAL { 0 }
    ::= { coord 14 }
 
--5.5.13    System Sync Control
systemSyncControl OBJECT-TYPE
    SYNTAX Integer32 (0..65535)
    UNITS "second"
    MAX-ACCESS read-write
    STATUS current
    DESCRIPTION "<Definition> This object is used to establish the system
        reference point for the Called System Pattern by providing the current
        position in the system pattern cycle (0-998 sec). The device shall
        recognize a write to this object as a command to establish the time
        until the next system reference point. Thereafter, the system
        reference point shall be assumed to occur at a frequency equal to the
        patternCycleTime.

        Values 999-65534 are not used. When the value in the object is 65535, the system REFERENCE point shall
        be referenced to the local Time Base in accordance with its
        programming.

        This CU must maintain an accuracy of 0.1 seconds based on the receipt
        of the SET packet. The device shall reset this object to ZERO when in
        BACKUP Mode. A write to this object shall reset the  Backup timer to
        ZERO (see unitBackupTime).
    <Object Identifier> 1.3.6.1.4.1.1206.4.2.1.4.15
    <Object Type> C"
    ::= { coord  15 }

--5.5.16    Unit Coordination Sync Point
unitCoordSyncPoint OBJECT-TYPE
    SYNTAX INTEGER { other (1),
                     firstPhaseGreenBegin (2),
                     lastPhaseGreenBegin (3),
                     firstPhaseGreenEnd (4),
                     lastPhaseGreenEnd (5),
                     firstPhaseYellowEnd (6),
                     lastPhaseYellowEnd (7) }
    MAX-ACCESS read-write
    STATUS deprecated
    DESCRIPTION "<Definition> This object is used to indicate the default coordination point for all timing patterns based on the first coordinated phase that turns on since the start of the timing pattern cycle or the last coordinated phase to turn on before the end of the timing pattern cycle. 
    The valid coordination sync points are:
        other: the coordination sync point is not described in this standard
        firstPhaseGreenBegin: the coordination point is the beginning of the
            Green indication of the first coordinated phase.
        lastPhaseGreenBegin: the coordination point is the beginning of the
            Green indication of the last coordinated phase.
        firstPhaseGreenEnd: the coordination point is end of the green
            indication of the first coordinated phase.
        lastPhaseGreenEnd: the coordination point is the end of the green
            indication of the last coordinated phase.
        firstPhaseYellowEnd: the coordination point is the end of the yellow
            indication of the first coordinated phase.
        lastPhaseYellowEnd: the coordination point is the end of the yellow
            indication of the last coordinated phase.
    <Object Identifier> 1.3.6.1.4.1.1206.4.2.1.4.16
    <Object Type> P"
    DEFVAL { firstPhaseGreenBegin }
    ::= { coord 16 }

--5.5.15    Coordination Current Offset
coordCurrentOffset OBJECT-TYPE
    SYNTAX Integer32 (0..65535)
    UNITS "second"
    MAX-ACCESS read-only
    STATUS current
    DESCRIPTION "<Definition> The value of the offset currently in effect from 0 to 998 seconds. This value value may change between or during cycles as a result of the CU coordination process transitioning to or maintaining the programmed pattern offset. This value may also change during the cycle as the result of a priority call. 
    
    Values 999-65534 are not used. A value of 65535 indicates that the controller is not in coordination because it is running Free or in preemption. 

    <Object Identifier> 1.3.6.1.4.1.1206.4.2.1.4.17
    <Object Type> S"
    REFERENCE "NEMA TS 2 Clause 3.6.2.2"
    ::= { coord 17 }

--5.5.16    Coordination Pattern Source
coordPatternSource OBJECT-TYPE
    SYNTAX BITS     {   other(0),
                        remote(1),
                        timebased(2),
                        frontPanel(3),
                        backup(4) }
    MAX-ACCESS read-only
    STATUS current
    DESCRIPTION "<Definition> This object indicates why the current pattern or mode is currently in effect. 
    Valid values are:
        other: the current pattern or mode was activated from a source not defined in this standard.
        remote: the current pattern or mode was commanded from a management locally or through a central system.
        timebased: the current pattern or mode is running as scheduled and not as a result of the CU going into backup mode. 
        frontPanel: the current pattern or mode was commanded from the front panel.
        backup: the current pattern or mode is running because the CU went into backup mode. The CU may go into backup mode due to a failure. 
    <Object Identifier> 1.3.6.1.4.1.1206.4.2.1.4.18
    <Object Type> S"
    ::= { coord 18 }

--5.6   Time Base Parameters
timebaseAsc OBJECT IDENTIFIER
    ::= { asc 5 }

-- This object is an identifier used to group all objects for support of timebase functions. If a device implements timebase functions then these objects shall be supported.

--5.6.1 Time Base Pattern Sync Parameter
timebaseAscPatternSync OBJECT-TYPE
    SYNTAX Integer32 (0..65535)
    UNITS "minute"
    MAX-ACCESS read-write
    STATUS current
    DESCRIPTION "<Definition> Pattern Sync Reference in minutes past midnight. This is the time that the master cycle begins and local cycle offset is relative. When the value is 65535, the controller unit shall use the Action time as the Sync Reference for that pattern. This value is defined in ISO 26048-1.
    <Object Identifier> 1.3.6.1.4.1.1206.4.2.1.5.1
    <Object Type> P"
    REFERENCE "NEMA TS 2 Clause 3.8.2"
    ::= { timebaseAsc 1 }

--5.6.2 Maximum Time Base Actions 
maxTimebaseAscActions OBJECT-TYPE
    SYNTAX Integer32 (1..255)
    UNITS "action"
    MAX-ACCESS read-only
    STATUS current
    DESCRIPTION "<Definition> The Maximum Number of Actions this device
        supports. This object indicates the maximum rows which shall appear
        in the timebaseAscActionTable object.
    <Object Identifier> 1.3.6.1.4.1.1206.4.2.1.5.2
    <Object Type> S"
    ::= { timebaseAsc 2 }

--5.6.3 Time Base Asc Action Table
timebaseAscActionTable OBJECT-TYPE
    SYNTAX SEQUENCE OF TimebaseAscActionEntry
    MAX-ACCESS not-accessible
    STATUS current
    DESCRIPTION "<Definition> A table containing Actuated Controller Unit Time
        Base action parameters. The number of rows in this table is equal to
        the maxTimebaseAscActions object.

        All the functionality of the timebaseAscActionTable is supported by patternTable. Previous versions of NTCIP 1202 only supported use of the timebaseAscActionTable to implement scheduled special functions. NTCIP 1202 v04 recommends using the patternTable to implement scheduled special functions as part of timing patterns but implementations that use the timebaseAscActionTable are still conformant. 

    <TableType> static
    <Object Identifier> 1.3.6.1.4.1.1206.4.2.1.5.3"
    ::= { timebaseAsc 3 }

timebaseAscActionEntry OBJECT-TYPE
    SYNTAX TimebaseAscActionEntry
    MAX-ACCESS not-accessible
    STATUS current
    DESCRIPTION "<Definition> Action Parameters for a Actuated Controller Unit
        Time Base Program.
    <Object Identifier> 1.3.6.1.4.1.1206.4.2.1.5.3.1"
    INDEX   { timebaseAscActionNumber }
    ::= { timebaseAscActionTable 1 }

TimebaseAscActionEntry ::= SEQUENCE { 
    timebaseAscActionNumber      Integer32,
    timebaseAscPattern           Integer32,
    timebaseAscAuxiliaryFunction Integer32, --deprecated
    timebaseAscSpecialFunction   Unsigned32,
    timebaseAscEnabledLane       Integer32 }

--5.6.3.1   Time Base Action Number
timebaseAscActionNumber OBJECT-TYPE
    SYNTAX Integer32 (1..255)
    UNITS "action"
    MAX-ACCESS not-accessible
    STATUS current
    DESCRIPTION "<Definition> The time base Action number for objects in this
        row. This value shall not exceed the maxTimebaseAscActions object
        value. This value may be referenced by ISO 26048-1. 
    <Object Identifier> 1.3.6.1.4.1.1206.4.2.1.5.3.1.1"
    ::= { timebaseAscActionEntry 1 }

--5.6.3.2   Time Base Action Pattern Parameter
timebaseAscPattern OBJECT-TYPE
    SYNTAX Integer32 (0..255)
    UNITS "pattern"
    MAX-ACCESS read-write
    STATUS current
    DESCRIPTION "<Definition> The Pattern that shall be active when this
        Action is active. The value shall not exceed the value of maxPatterns,
        except for 254 (Free) and 255 (Flash). A pattern of zero indicates that no pattern
        is being selected. A pattern = 0 relinquishes control to entity of a
        lower priority than timebase and allows that entity to control (i.e.,
        interconnect if available).
    <Object Identifier> 1.3.6.1.4.1.1206.4.2.1.5.3.1.2
    <Object Type> P"
    ::= { timebaseAscActionEntry 2 }

--5.6.3.3   Time Base Action Auxiliary Function Parameter
timebaseAscAuxiliaryFunction OBJECT-TYPE
    SYNTAX Integer32 (0..255)
    MAX-ACCESS read-write
    STATUS deprecated
    DESCRIPTION "<Definition> The Auxiliary functions that shall be active
        when this Action is active.

        Bit 7: Reserved
        Bit 6: Reserved
        Bit 5: Reserved
        Bit 4: Reserved
        Bit 3: Dimming enabled if set (non-zero), disabled if clear (zero).
            For dimming to occur, this control AND ('unitControl' OR a dimming
            input) must be True.
        Bit 2: Auxiliary Function 3 enabled if set (non-zero), disabled if
            clear (zero).
        Bit 1: Auxiliary Function 2 enabled if set (non-zero), disabled if
            clear (zero).
        Bit 0: Auxiliary Function 1 enabled if set (non-zero), disabled if
            clear (zero).

        A SET of a 'reserved' bit to a value other than zero (0) shall return
        a badValue(3) error.
    <Object Identifier> 1.3.6.1.4.1.1206.4.2.1.5.3.1.3
    <Object Type> P"
    ::= { timebaseAscActionEntry 3 }

--5.6.3.3   Time Base Action Special Function Parameter
timebaseAscSpecialFunction OBJECT-TYPE
    SYNTAX Unsigned32 (0..4294967295)
    MAX-ACCESS read-write
    STATUS current
    DESCRIPTION "<Definition> The Special Functions that shall be active when this Action is active. Each bit represents a special function from 1 to 32. 
        Bit 31: Special Function 32
        Bit 30: Special Function 31
        Bit 29: Special Function 30
        .... .... .... .... .....
        Bit 3: Special Function 4
        Bit 2: Special Function 3
        Bit 1: Special Function 2
        Bit 0: Special Function 1

        Bit = 0 - False/Disabled, Bit = 1 - True/Enabled

        If the ASC supports less than 32 special functions, a SET of a bit for an unsupported special function shall return a badValue(3) error.
    <Object Identifier> 1.3.6.1.4.1.1206.4.2.1.5.3.1.4"
    ::= { timebaseAscActionEntry 4 }

--5.6.3.4   Time Base Action Enabled Lane
timebaseAscEnabledLane OBJECT-TYPE
    SYNTAX Integer32 (0..255)
    MAX-ACCESS read-write
    STATUS current
    DESCRIPTION "<Definition> This value is equal to the enabledLaneIndex
        (row) in the spatEnabledLanesConcurrencyTable that contains the
        enabledLaneConcurrency lanes to be active when this Action is active.
        A value of zero indicates that no lanes are to be be enabled as part
        of this action.
    <Object Identifier> 1.3.6.1.4.1.1206.4.2.1.5.3.1.4
    <Object Type> P"
    ::= { timebaseAscActionEntry 5 }

--5.6.4 Time Base Asc Action Status
timebaseAscActionStatus OBJECT-TYPE
    SYNTAX Integer32 (0..255)
    MAX-ACCESS read-only
    STATUS current
    DESCRIPTION "<Definition> This object indicates the current time base
        Action Table row that will be used when the CU is in Time Base
        operation. A value of zero indicates that no time base Action is
        selected.
    <Object Identifier> 1.3.6.1.4.1.1206.4.2.1.5.4
    <Object Type> S"
    ::= { timebaseAsc 4 }

--5.6.5 Action Plan Command
actionPlanControl OBJECT-TYPE
    SYNTAX Integer32 (0..255)
    MAX-ACCESS read-write
    STATUS current
    DESCRIPTION "<Definition> This object is used to activate a configured
        action plan by referencing the Action number (timebaseAscActionNumber).
        When this action plan is in effect, the CU shall operate as if the
        action plan has been activated by the time base scheduler. A value of
        0 shall deactivate the action plan and returns to what would normally
        have been in operation if the action plan was not in effect.

        If an unsupported / invalid Action number is called, Free shall be the
        operational mode.

        The device shall reset this object to ZERO when in BACKUP Mode. A
        write to this object shall reset the Backup timer to ZERO (see
        unitBackupTime).
    <Object Identifier> 1.3.6.1.4.1.1206.4.2.1.5.5
    <Object Type> C"
    DEFVAL { 0 }
    ::= { timebaseAsc 5 }

--5.7   Preempt Parameters
preempt OBJECT IDENTIFIER
    ::= { asc 6 }

-- The preempt node contains objects that support preempt input functions for the device.

--5.7.1 Maximum Preempts
maxPreempts OBJECT-TYPE
    SYNTAX Integer32 (1..255)
    UNITS "preempt"
    MAX-ACCESS read-only
    STATUS current
    DESCRIPTION "<Definition> The Maximum Number of Preempts this Actuated Controller Unit supports. This object indicates the maximum rows which shall appear in the preemptTable object.
    <Object Identifier> 1.3.6.1.4.1.1206.4.2.1.6.1
    <Object Type> S"
    REFERENCE "NEMA TS 2 Clause 3.7"
    ::= { preempt 1 }

--5.7.2 Preempt Table
preemptTable OBJECT-TYPE
    SYNTAX SEQUENCE OF PreemptEntry
    MAX-ACCESS not-accessible
    STATUS current
    DESCRIPTION "<Definition> A table containing Actuated Controller Unit preemption parameters. The number of rows in this table is equal to the maxPreempts object.
    <TableType> static
    <Object Identifier> 1.3.6.1.4.1.1206.4.2.1.6.2"
    ::= { preempt 2 }

preemptEntry OBJECT-TYPE
    SYNTAX PreemptEntry
    MAX-ACCESS not-accessible
    STATUS current
    DESCRIPTION "<Definition> Parameters for a specific Actuated Controller Unit preemptor.
    <Object Identifier> 1.3.6.1.4.1.1206.4.2.1.6.2.1"
    INDEX    { preemptNumber }
    ::= { preemptTable 1}

PreemptEntry ::= SEQUENCE {
    preemptNumber            Integer32,
    preemptControl           Integer32,
    preemptLink              Integer32,
    preemptDelay             Integer32,
    preemptMinimumDuration   Integer32,
    preemptMinimumGreen      Integer32,
    preemptMinimumWalk       Integer32,
    preemptEnterPedClear     Integer32,
    preemptTrackGreen        Integer32,
    preemptDwellGreen        Integer32,
    preemptMaximumPresence   Integer32,
    preemptTrackPhase        OCTET STRING,
    preemptDwellPhase        OCTET STRING,
    preemptDwellPed          OCTET STRING,
    preemptExitPhase         OCTET STRING,
    preemptState             INTEGER,
    preemptTrackOverlap      OCTET STRING,
    preemptDwellOverlap      OCTET STRING,
    preemptCyclingPhase      OCTET STRING,
    preemptCyclingPed        OCTET STRING,
    preemptCyclingOverlap    OCTET STRING,
    preemptEnterYellowChange Integer32,
    preemptEnterRedClear     Integer32,
    preemptTrackYellowChange Integer32,
    preemptTrackRedClear     Integer32,
    preemptSequenceNumber    Integer32,
    preemptExitType          INTEGER }

--5.7.2.1   Preempt Number
preemptNumber OBJECT-TYPE
    SYNTAX Integer32 (1..255)
    UNITS "preempt"
    MAX-ACCESS not-accessible
    STATUS current
    DESCRIPTION "<Definition> The preempt number for objects in this row. The value shall not exceed the maxPreempts object value. When all preemptControl objects have a value where bit 2 = 0, each preemptNumber routine shall be a higher priority and override all preemptNumber routines that have a larger preemptNumber.

When a preemptControl object has a value where bit 2 = 1, the next higher preemptNumber becomes of equal priority with the preemptNumber but may still be a higher priority than larger preemptNumbers depending on bit 2 of the relavent preemptControl objects.
    <Object Identifier> 1.3.6.1.4.1.1206.4.2.1.6.2.1.1"
    ::= { preemptEntry 1 }

--5.7.2.2   Preempt Control Parameter
preemptControl OBJECT-TYPE
    SYNTAX Integer32 (0..255)
    MAX-ACCESS read-write
    STATUS current
    DESCRIPTION "<Definition> Preempt Miscellaneous Control Parameter Mask (Bit=0: False/Disabled, Bit=1: True/Enabled) as follows:
Bit 7: Reserved
Bit 6: All Red Entry - the CU shall enter to all red at the start of the preempt. 
Bit 5: All Red Flash Exit - the CU shall enter to all red flash instead of normal operations when the preemptMaximumPresence is exceeded. When this bit is not set (0), the CU shall exit the preempt as specified in preemptExitType. 
Bit 4: Preempt Enable - enables or disables this preemption input. Disabling preempts should be done with extreme caution.
Bit 3: Flash Dwell - the CU shall cause the phases listed in the preemptDwellPhase object to flash Yellow during the Dwell interval. All active phases not listed in preemptDwellPhase shall flash Red.
The CU shall cause the overlaps listed in the preemptDwellOverlap object to flash Yellow during the Dwell state. All active overlaps not listed in preemptDwellOverlap shall flash Red. Preempt cycling phase programming is ignored if this bit is set. This control is optional.
Bit 2: Preempt Override Preempt Lock- provide a means to define whether this preempt shall NOT override the next higher numbered Preempt (preemptNumber + 1). When this bit is set (1), this preempt shall not override the next higher numbered preempt. Lowered numbered preempts override higher numbered preempts. For example, 1 overrides 3, and the only way to get 3 equal to 1, is to set both 1 and 2 to NOT override the next higher numbered preempt. This parameter shall be ignored when preemptNumber equals maxPreempts.
Bit 1: Preempt Override Flash Lock - provide a means to define whether this preempt shall NOT override Automatic Flash. When set (1) this preempt shall NOT override Automatic Flash.
Bit 0: Non-Locking Memory - provide a means to enable an operation which does not require detector memory. When set (1) a preempt sequence shall not occur if the preempt input terminates prior to expiration of the preemptDelay time.
    
    A SET of a 'reserved' bit to a value other than zero (0) shall return a badValue(3) error. 
    
    <Object Identifier> 1.3.6.1.4.1.1206.4.2.1.6.2.1.2
    <Object Type> P"
    REFERENCE "NEMA TS 2 Clause 3.7.2.1 and 3.7.2.2"
    DEFVAL { 0 }
    ::= { preemptEntry 2 }

--5.7.2.3   Preempt Link Parameter
preemptLink OBJECT-TYPE
    SYNTAX Integer32 (0..255)
    UNITS "preempt"
    MAX-ACCESS read-write
    STATUS current
    DESCRIPTION "<Definition> This object provides a means to define a higher priority preempt to be combined (linked) with this preempt. At the end of preemptDwellGreen, the linked preempt shall receive an automatic call that shall be maintained as long as the demand for this preempt is active. Any value that is not a higher priority preempt or a valid preempt shall be ignored. The value shall not exceed the maxPreempts object value.
    <Object Identifier> 1.3.6.1.4.1.1206.4.2.1.6.2.1.3
    <Object Type> P"
    DEFVAL { 0 }
    ::= { preemptEntry 3 }

--5.7.2.4   Preempt Delay Parameter
preemptDelay OBJECT-TYPE
    SYNTAX Integer32 (0..255)
    UNITS "second"
    MAX-ACCESS read-write
    STATUS current
    DESCRIPTION "<Definition> Preempt Delay Time in seconds (0-999 sec). This value determines the time the preempt input shall be active prior to initiating any preempt sequence. A non-locking preempt input which is removed prior to the completion of this time shall not cause a preempt sequence to occur.
    <Object Identifier> 1.3.6.1.4.1.1206.4.2.1.6.2.1.4
    <Object Type> P"
    DEFVAL { 0 }
    ::= { preemptEntry 4 }

--5.7.2.5   Preempt Duration Parameter
preemptMinimumDuration OBJECT-TYPE
    SYNTAX Integer32 (0..65535)
    UNITS "second"
    MAX-ACCESS read-write
    STATUS current
    DESCRIPTION "<Definition> Preempt Minimum Duration Time in seconds. This value determines the minimum time during which the preempt is active. Duration begins timing at the end of Preempt Delay (if non zero) and will prevent an exit from the Dwell interval until this time has elapsed.
    <Object Identifier> 1.3.6.1.4.1.1206.4.2.1.6.2.1.5
    <Object Type> P"
    DEFVAL { 0 }
    ::= { preemptEntry 5 }

--5.7.2.6   Preempt Minimum Green Parameter
preemptMinimumGreen OBJECT-TYPE
    SYNTAX Integer32 (0..255)
    UNITS "second"
    MAX-ACCESS read-write
    STATUS current
    DESCRIPTION "<Definition> Preempt Minimum Green Time in seconds (0-255 sec). A preempt initiated transition shall not cause the termination of an existing GREEN indication for lesser of the phase's Minimum Green time or this period. CAUTION - if this value is zero, the currently active phases' GREEN indications are terminated immediately.
    <Object Identifier> 1.3.6.1.4.1.1206.4.2.1.6.2.1.6
    <Object Type> P"
    DEFVAL { 255 }
    ::= { preemptEntry 6 }

--5.7.2.7   Preempt Minimum Walk Parameter
preemptMinimumWalk OBJECT-TYPE
    SYNTAX Integer32 (0..255)
    UNITS "second"
    MAX-ACCESS read-write
    STATUS current
    DESCRIPTION "<Definition> Preempt Minimum Walk Time in seconds (0-255 sec). A preempt initiated transition shall not cause the termination of an existing WALK prior to its display for the lesser of the phase's Walk time or this period. CAUTION - if this value is zero, currently active phases' WALK indications are terminated immediately.
    <Object Identifier> 1.3.6.1.4.1.1206.4.2.1.6.2.1.7
    <Object Type> P"
    DEFVAL { 255 }
    ::= { preemptEntry 7 }

--5.7.2.8   Preempt Enter Pedestrian Clear Parameter
preemptEnterPedClear OBJECT-TYPE
    SYNTAX Integer32 (0..255)
    UNITS "second"
    MAX-ACCESS read-write
    STATUS current
    DESCRIPTION "<Definition> Enter Ped Clearance Time in seconds (0-255 sec). This parameter controls the ped clear timing for a normal Walk signal terminated by a preempt initiated transition. A preempt initiated transition shall not cause the termination of a Pedestrian Clearance (Flashing DON'T WALK) prior to its display for the lesser of the phase's Pedestrian Clearance time or this period. CAUTION - currently active phases' Pedestrian Clearance indications are terminated immediately or skipped.
    <Object Identifier> 1.3.6.1.4.1.1206.4.2.1.6.2.1.8
    <Object Type> P"
    DEFVAL { 255 }
    ::= { preemptEntry 8 }

--5.7.2.9   Preempt Track Green Parameter
preemptTrackGreen OBJECT-TYPE
    SYNTAX Integer32 (0..255)
    UNITS "second"
    MAX-ACCESS read-write
    STATUS current
    DESCRIPTION "<Definition> Track Clear Green Time in seconds (0-255 sec). This parameter controls the green timing for the track clearance movement. Track Clear phase(s) are enabled in the preemptTrackPhase object. If this value is zero, the track clearance movement is omitted, regardless of preemptTrackPhase programming.
    <Object Identifier> 1.3.6.1.4.1.1206.4.2.1.6.2.1.9
    <Object Type> P"
    DEFVAL { 0 }
    ::= { preemptEntry 9 }

--5.7.2.10  Preempt Minimum Dwell Parameter
preemptDwellGreen OBJECT-TYPE
    SYNTAX Integer32 (0..255)
    UNITS "second"
    MAX-ACCESS read-write
    STATUS current
    DESCRIPTION "<Definition> Minimum Dwell interval in seconds (1-255 sec). This parameter controls the minimum timing for the dwell interval. Phase(s) active during the Dwell interval are enabled in preemptDwellPhase and preemptCyclingPhase objects. Dwell phases may dwell for this amount of time before any phases cycle during the preempt. The Dwell interval shall not terminate prior to the completion of preemptMinimumDuration, preemptDwellGreen (this object), and the call is no longer present.
    <Object Identifier> 1.3.6.1.4.1.1206.4.2.1.6.2.1.10
    <Object Type> P"
    DEFVAL { 0 }
    ::= { preemptEntry 10 }

--5.7.2.11  Preempt Maximum Presence Parameter
preemptMaximumPresence OBJECT-TYPE
    SYNTAX Integer32 (0..65535)
    UNITS "second"
    MAX-ACCESS read-write
    STATUS current
    DESCRIPTION "<Definition> Preempt Maximum Presence time in seconds (0-65535 sec). This value determines the maximum time which a preempt call may remain active and be considered valid. When the preempt call has been active for this time period, the CU shall return to normal operation. This preempt call shall be considered invalid until such time as a change in state occurs (no longer active). When set to zero the preempt maximum presence time is disabled.
    <Object Identifier> 1.3.6.1.4.1.1206.4.2.1.6.2.1.11
    <Object Type> P"
    DEFVAL { 0 }
    ::= { preemptEntry 11 }

--5.7.2.12  Preempt Track Phase Parameter
preemptTrackPhase OBJECT-TYPE
    SYNTAX OCTET STRING
    MAX-ACCESS read-write
    STATUS current
    DESCRIPTION "<Definition> Each octet within the octet string contains a phaseNumber(binary value) that shall be active during the Preempt Track Clearance intervals. The values of phaseNumber used here shall not exceed maxPhases or violate the Consistency Checks defined in Section 4.3.2.
    <Object Identifier> 1.3.6.1.4.1.1206.4.2.1.6.2.1.12
    <Object Type> P2"
    DEFVAL { "" }
    ::= { preemptEntry 12 }

--5.7.2.13  Preempt Dwell Phase Parameter
preemptDwellPhase OBJECT-TYPE
    SYNTAX OCTET STRING
    MAX-ACCESS read-write
    STATUS current
    DESCRIPTION "<Definition> Each octet within the octet string contains a phaseNumber (binary value) that specifies the phase(s) to be served in the Preempt Dwell interval. The phase(s) defined in preemptCyclingPhase shall occur after those defined herein. The values of phaseNumber used here shall not exceed maxPhases or violate the Consistency Checks defined in Section 4.3.2.
    <Object Identifier> 1.3.6.1.4.1.1206.4.2.1.6.2.1.13
    <Object Type> P2"
    DEFVAL { "" }
    ::= { preemptEntry 13 }

--5.7.2.14  Preempt Dwell Ped Parameter
preemptDwellPed OBJECT-TYPE
    SYNTAX OCTET STRING
    MAX-ACCESS read-write
    STATUS current
    DESCRIPTION "<Definition> Each octet within the octet string contains a phaseNumber (binary value) that specifies the pedestrian movement(s) to be served in the Preempt Dwell interval. The peds defined in preemptCyclingPed shall occur after those defined herein. The values of phaseNumber used here shall not exceed maxPhases or violate the Consistency Checks defined in Section 4.3.2.
    <Object Identifier> 1.3.6.1.4.1.1206.4.2.1.6.2.1.14
    <Object Type> P2"
    DEFVAL { "" }
    ::= { preemptEntry 14 }

--5.7.2.15  Preempt Exit Phase Parameter
preemptExitPhase OBJECT-TYPE
    SYNTAX OCTET STRING
    MAX-ACCESS read-write
    STATUS current
    DESCRIPTION "<Definition> Each octet within the octet string contains a phaseNumber (binary value) that shall be active following Preempt. The values of phaseNumber used here shall not exceed maxPhases or violate the Consistency Checks defined in Section 4.3.2.
    <Object Identifier> 1.3.6.1.4.1.1206.4.2.1.6.2.1.15
    <Object Type> P2"
    DEFVAL { "" }
    ::= { preemptEntry 15 }

--5.7.2.16  Preempt State
preemptState OBJECT-TYPE
    SYNTAX INTEGER { other (1),
    notActive (2),
    notActiveWithCall (3),
    entryStarted (4),
    trackService (5),
    dwell (6),
    linkActive (7),
    exitStarted (8),
    maxPresence (9),
    advancedPreempt (10) }
    MAX-ACCESS read-only
    STATUS current
    DESCRIPTION "<Definition> Preempt State provides status on which state the associated preempt is in. The states are as follows:
other: preempt service is not specified in this standard.
notActive: preempt input is not active, this preempt is not active.
notActiveWithCall: preempt input is active, preempt service has not started.
entryStarted: preempt service is timing the entry intervals.
trackService: preempt service is timing the track intervals.
dwell: preempt service is timing the dwell intervals.
linkActive: preempt service is performing linked operation.
exitStarted: preempt service is timing the exit intervals.
maxPresence: preempt input has exceeded maxPresence time
advancedPreempt: preempt service is timing the advanced preemption time.
    <Object Identifier> 1.3.6.1.4.1.1206.4.2.1.6.2.1.16
    <Object Type> S"
    ::= { preemptEntry 16}

--5.7.2.17  Preempt Track Overlap Parameter
preemptTrackOverlap OBJECT-TYPE
    SYNTAX OCTET STRING
    MAX-ACCESS read-write
    STATUS current
    DESCRIPTION "<Definition> Each octet within the octet string contains an overlapNumber (binary value) that shall be active during the Preempt Track Clear intervals. The values of overlapNumber used here shall not exceed maxOverlaps or violate the consistency checks defined in Section 4.3.2. Any overlap not specified will not be active during the preempt even if its parent phases are active.
    <Object Identifier> 1.3.6.1.4.1.1206.4.2.1.6.2.1.17
    <Object Type> P2"
    DEFVAL { "" }
    ::= { preemptEntry 17 }

--5.7.2.18  Preempt Dwell Overlap Parameter
preemptDwellOverlap OBJECT-TYPE
    SYNTAX OCTET STRING
    MAX-ACCESS read-write
    STATUS current
    DESCRIPTION "<Definition> Each octet within the octet string contains an overlapNumber (binary value) that is allowed during the Preempt Dwell interval. The values of overlapNumber used here shall not exceed maxOverlaps or violate the consistency checks defined in Section 4.3.2. Any overlap not specified will not be active during the preempt even if its parent phases are active.
    <Object Identifier> 1.3.6.1.4.1.1206.4.2.1.6.2.1.18
    <Object Type> P2"
    DEFVAL { "" }
    ::= { preemptEntry 18 }

--5.7.2.19  Preempt Cycling Phase Parameter
preemptCyclingPhase OBJECT-TYPE
    SYNTAX OCTET STRING
    MAX-ACCESS read-write
    STATUS current
    DESCRIPTION "<Definition> Each octet within the octet string contains a phaseNumber (binary value) that is allowed to cycle during the Preempt Dwell interval after preemptDwellTime has lapsed. The values of phaseNumber used here shall not exceed maxPhases or violate the Consistency Checks defined in Section 4.3.2.
    <Object Identifier> 1.3.6.1.4.1.1206.4.2.1.6.2.1.19
    <Object Type> P2"
    DEFVAL { "" }
    ::= { preemptEntry 19 }

--5.7.2.20  Preempt Cycling Ped Parameter
preemptCyclingPed OBJECT-TYPE
    SYNTAX OCTET STRING
    MAX-ACCESS read-write
    STATUS current
    DESCRIPTION "<Definition> Each octet within the octet string contains a phaseNumber (binary value) indicating a pedestrian movement that is allowed to cycle during the Preempt Dwell interval after preemptDwellTime has lapsed. The values of phaseNumber used here shall not exceed maxPhases or violate the consistency checks defined in Section 4.3.2.
    <Object Identifier> 1.3.6.1.4.1.1206.4.2.1.6.2.1.20
    <Object Type> P2"
    DEFVAL { "" }
    ::= { preemptEntry 20 }

--5.7.2.21  Preempt Cycling Overlap Parameter
preemptCyclingOverlap OBJECT-TYPE
    SYNTAX OCTET STRING
    MAX-ACCESS read-write
    STATUS current
    DESCRIPTION "<Definition> Each octet within the octet string contains a overlapNumber (binary value) that is allowed to cycle during the Preempt Dwell interval. The values of overlapNumber used here shall not exceed maxOverlaps or violate the consistency checks defined in Section 4.3.2. Any overlap not specified will not be active during the preempt even if its parent phases are active.
    <Object Identifier> 1.3.6.1.4.1.1206.4.2.1.6.2.1.21
    <Object Type> P2"
    DEFVAL { "" }
    ::= { preemptEntry 21 }

--5.7.2.22  Preempt Enter Yellow Change Parameter
preemptEnterYellowChange OBJECT-TYPE
    SYNTAX Integer32 (0..255)
    UNITS "decisecond"
    MAX-ACCESS read-write
    STATUS current
    DESCRIPTION "<Definition> Enter Yellow Change in tenth seconds (0-25.5  sec). This parameter controls the yellow change timing for a normal Yellow Change signal terminated by a preempt initiated transition. A preempt initiated transition shall not cause the termination of a Yellow Change prior to its display for the lesser of the phase's Yellow Change time or this period. CAUTION - if this value is zero, phase Yellow Change is terminated immediately.
    <Object Identifier> 1.3.6.1.4.1.1206.4.2.1.6.2.1.22
    <Object Type> P"
    DEFVAL { 255 }
    ::= { preemptEntry 22 }

--5.7.2.23  Preempt Enter Red Clearance Parameter
preemptEnterRedClear OBJECT-TYPE
    SYNTAX Integer32 (0..255)
    UNITS "decisecond"
    MAX-ACCESS read-write
    STATUS current
    DESCRIPTION "<Definition> Enter Red Clear in tenth seconds (0-25.5 sec). This parameter controls the red clearance timing for a normal Red Clear signal terminated by a preempt initiated transition. A preempt initiated transition shall not cause the termination of a Red Clear prior to its display for the lesser of the phase's Red Clear time or this period. CAUTION - if this value is zero, phase Red Clear is terminated immediately.
    <Object Identifier> 1.3.6.1.4.1.1206.4.2.1.6.2.1.23
    <Object Type> P"
    DEFVAL { 255 }
    ::= { preemptEntry 23 }

--5.7.2.24  Preempt Track Yellow Change Parameter
preemptTrackYellowChange OBJECT-TYPE
    SYNTAX Integer32 (0..255)
    UNITS "decisecond"
    MAX-ACCESS read-write
    STATUS current
    DESCRIPTION "<Definition> Track Clear Yellow Change time in tenth seconds (0-25.5 sec). The lesser of the phase's Yellow Change time or this parameter controls the yellow timing for the track clearance movement. Track clear phases are specified in the preemptTrackPhase object. The track clearance movement is enabled in the preemptTrackGreen object. 
    <Object Identifier> 1.3.6.1.4.1.1206.4.2.1.6.2.1.24
    <Object Type> P"
    DEFVAL { 255 }
    ::= { preemptEntry 24 }

--5.7.2.25  Preempt Track Red Clearance Parameter
preemptTrackRedClear OBJECT-TYPE
    SYNTAX Integer32 (0..255)
    UNITS "decisecond"
    MAX-ACCESS read-write
    STATUS current
    DESCRIPTION "<Definition> Track Clear Red Clearance time in tenth seconds (0-25.5 sec). The lesser of the phase's Red Clearance time or this parameter controls the Red Clearance timing for the track clearance movement. Track clear phases are specified in the preemptTrackPhase object. The track clearance movement is enabled in the preemptTrackGreen object. 
    <Object Identifier> 1.3.6.1.4.1.1206.4.2.1.6.2.1.25
    <Object Type> P"
    DEFVAL { 255 }
    ::= { preemptEntry 25 }

--5.7.2.26  Preempt Sequence Number
preemptSequenceNumber OBJECT-TYPE
    SYNTAX Integer32 (0..255)
    UNITS "sequence"
    MAX-ACCESS read-write
    STATUS current
    DESCRIPTION "<Definition> This object is used to configure the sequence to run during the preempt's dwell duration. The selected sequence defines the order in which the phases defined the preemptCyclingPhase and preemptCyclingPed objects are allowed to cycle. Phases in the selected sequence that are not defined in preemptCyclingPhase nor preemptCyclingPed do not cycle. 

This value is a sequenceNumber used to select a sequence from the sequenceTable and shall not exceed the maxSequences object value. A value of zero indicates that the sequence to run is the one that was in effect when the preempt was activated.

    <Object Identifier> 1.3.6.1.4.1.1206.4.2.1.6.2.1.26
    <Object Type> P"
    DEFVAL { 0 }
    ::= { preemptEntry 26 }

--5.7.2.27  Preempt Exit Type
preemptExitType OBJECT-TYPE
    SYNTAX INTEGER { exitPhases (1),
    queueDelayRecovery (2),
    shortService (3),
    exitCoord (4)} 
    MAX-ACCESS read-write
    STATUS current 
    DESCRIPTION "<Definition> This object defines the exit strategy (type) to be used following the end of the preempt. The exit types are as follows: 
exitPhases: the CU immediately enters the exit phases to be active as configured
queueDelayRecovery: the CU immediately enters the phase with the highest demand or longest wait time 
shortService: the CU immediately enters the first short service phase. The first short service phase is a phase where only the preempt minimum green time was serviced during the advanced preemption time or the right-of-way transfer time
exitCoord: the CU immediately returns to the place in the coordinated cycle where the ASC would have been if there was no preempt 
    <Object Type> P
    <Object Identifier> 1.3.6.1.4.1.1206.4.2.1.6.2.1.27"
    ::= { preemptEntry 27 }

--5.7.3 Preempt Control Table
preemptControlTable OBJECT-TYPE
    SYNTAX SEQUENCE OF PreemptControlEntry
    MAX-ACCESS not-accessible
    STATUS current
    DESCRIPTION "<Definition> This table contains the control objects that allow the preempts to be activated remotely. There shall be one control object for each preempt input supported by the device. The number of rows in this table shall be equal to maxPreempts.
    <TableType> static
    <Object Identifier> 1.3.6.1.4.1.1206.4.2.1.6.3"
    ::= { preempt 3 }

preemptControlEntry OBJECT-TYPE
    SYNTAX PreemptControlEntry
    MAX-ACCESS not-accessible
    STATUS current
    DESCRIPTION "<Definition> Control objects for each preempt input. These objects allow the system to activate preempt functions remotely.
    <Object Identifier> 1.3.6.1.4.1.1206.4.2.1.6.3.1"
    INDEX   { preemptControlNumber }
    ::= { preemptControlTable 1 }

PreemptControlEntry ::= SEQUENCE { 
    preemptControlNumber Integer32,
    preemptControlState  Integer32 }

--5.7.3.1   Preempt Control Number
preemptControlNumber OBJECT-TYPE
    SYNTAX Integer32 (1..255)
    UNITS "preempt"
    MAX-ACCESS not-accessible
    STATUS current
    DESCRIPTION "<Definition> This object shall indicate the preempt input number controlled by the associated preemptControlState object in this row.
    <Object Identifier> 1.3.6.1.4.1.1206.4.2.1.6.3.1.1"
    ::= { preemptControlEntry  1 }

--5.7.3.2   Preempt Control State
preemptControlState OBJECT-TYPE
    SYNTAX Integer32 (0..1)
    MAX-ACCESS read-write
    STATUS current
    DESCRIPTION "<Definition> This object when set to ON (one) shall cause the associated preempt actions to occur unless the actions have already been started by the physical preempt input. The preempt shall remain active as long as this object is ON or the physical preempt input is ON. This object when set to OFF (zero) shall cause the physical preempt input to control the associated preempt actions. The device shall reset this object to ZERO when in BACKUP Mode. A write to this object shall reset the Backup timer to ZERO (see unitBackupTime).
    <Object Identifier> 1.3.6.1.4.1.1206.4.2.1.6.3.1.2
    <Object Type> C"
    ::= { preemptControlEntry  2 }

--5.7.4 Preempt Status
preemptStatus OBJECT-TYPE 
    SYNTAX Integer32 (0..255)
    MAX-ACCESS read-only 
    STATUS current 
    DESCRIPTION "<Definition> This object defines the preempt number that is currently being serviced in the device. A value of zero indicate no preempt is being served. 
    <Object Identifier> 1.3.6.1.4.1.1206.4.2.1.6.4" 
    ::= { preempt 4 }

--5.7.5 Maximum Preempt Groups
maxPreemptGroups OBJECT-TYPE
    SYNTAX Integer32 (1..32)
    UNITS "group"
    MAX-ACCESS read-only
    STATUS current
    DESCRIPTION "<Definition> The Maximum Number of Preempt Groups (8 Preempt per group) this CU supports. This value is equal to TRUNCATE [(maxPreempts + 7) / 8]. This object indicates the maximum rows which shall appear in the preemptStatusGroupTable.
    <Object Identifier> 1.3.6.1.4.1.1206.4.2.1.6.5
    <Object Type> S"
    ::= { preempt 5 }

--5.7.6 Preempt Status Table
preemptStatusGroupTable OBJECT-TYPE
    SYNTAX SEQUENCE OF PreemptStatusGroupEntry
    MAX-ACCESS not-accessible
    STATUS current
    DESCRIPTION "<Definition> A table containing the CU preempt input signal status in groups of eight Preempts. The number of rows in this table is equal to the maxPreemptGroups object.
    <TableType> static
    <Object Identifier> 1.3.6.1.4.1.1206.4.2.1.6.6"
    ::= { preempt 6 }

preemptStatusGroupEntry OBJECT-TYPE
    SYNTAX PreemptStatusGroupEntry
    MAX-ACCESS not-accessible
    STATUS current
    DESCRIPTION "<Definition> Preempt input signal status for preempt inputs in groups of eight.
    <Object Identifier> 1.3.6.1.4.1.1206.4.2.1.6.6.1"
    INDEX { preemptStatusGroupNumber }
    ::= { preemptStatusGroupTable 1 }

PreemptStatusGroupEntry ::= SEQUENCE {
    preemptStatusGroupNumber Integer32,
    preemptStatusGroup       Integer32  }

--5.7.6.1   Preempt Status Group Number
preemptStatusGroupNumber OBJECT-TYPE
    SYNTAX Integer32 (1..32)
    UNITS "group"
    MAX-ACCESS not-accessible
    STATUS current
    DESCRIPTION "<Definition> The Preempt StatusGroup number for objects in this row. This value shall not exceed the maxPreemptGroups object value.
    <Object Identifier> 1.3.6.1.4.1.1206.4.2.1.6.6.1.1
    <Object Type> S"
    ::= { preemptStatusGroupEntry 1 }

--5.7.6.2   Preempt Status Group
preemptStatusGroup OBJECT-TYPE
    SYNTAX Integer32 (0..255)
    MAX-ACCESS read-only
    STATUS current
    DESCRIPTION "<Definition> Preempt Input Signal Status Mask. When a bit = 1, a preempt input signal is detected or the preemptControlState is ON for that input, and when a bit = 0, no preempt input signal is detected and the preemptControlState is OFF for that input.
Bit 7: Preempt # = (preemptStatusGroupNumber * 8)
Bit 6: Preempt # = (preemptStatusGroupNumber * 8) - 1
Bit 5: Preempt # = (preemptStatusGroupNumber * 8) - 2
Bit 4: Preempt # = (preemptStatusGroupNumber * 8) - 3
Bit 3: Preempt # = (preemptStatusGroupNumber * 8) - 4
Bit 2: Preempt # = (preemptStatusGroupNumber * 8) - 5
Bit 1: Preempt # = (preemptStatusGroupNumber * 8) - 6
Bit 0: Preempt # = (preemptStatusGroupNumber * 8) - 7

    <Object Identifier> 1.3.6.1.4.1.1206.4.2.1.6.6.1.2
    <Object Type> S"
    ::= { preemptStatusGroupEntry 2 }

--5.7.7 Preempt Queue Delay Table
preemptQueueDelayTable OBJECT-TYPE
    SYNTAX SEQUENCE OF PreemptQueueDelayEntry
    MAX-ACCESS not-accessible
    STATUS current
    DESCRIPTION "<Definition> A table containing CU detector parameters for the queue delay recovery exit strategy. The number of rows in this table will not exceed the maxVehicleDetectors object.
    <TableType> static
    <Object Identifier> 1.3.6.1.4.1.1206.4.2.1.6.7"
    ::= { preempt 7 }

preemptQueueDelayEntry OBJECT-TYPE
    SYNTAX PreemptQueueDelayEntry
    MAX-ACCESS not-accessible
    STATUS current
    DESCRIPTION "<Definition> Parameters for a specific CU preempt input if the queue delay recovery exit strategy is used.
    <Object Identifier> 1.3.6.1.4.1.1206.4.2.1.6.7.1"
    INDEX { preemptNumber, vehicleDetectorNumber }
    ::= { preemptQueueDelayTable 1}

PreemptQueueDelayEntry ::= SEQUENCE {
    preemptDetectorWeight Integer32 }

--5.7.7.1   Preempt Detector Weight
preemptDetectorWeight OBJECT-TYPE 
    SYNTAX Integer32 (0..1000) 
    MAX-ACCESS read-write 
    STATUS current 
    DESCRIPTION "<Definition> This object defines the relative weight for the associated detector when using the detector data to determine the queue delay recovery exit strategy from a preempt input. The association between the vehicleDetectorNumber and a phase is identified by the vehicleDetectorCallPhase. A higher number for this object indicates a larger weight for the demand and wait time for that phase.
    <Object Identifier> 1.3.6.1.4.1.1206.4.2.1.6.7.1.1
    <Object Type> P"
    ::= { preemptQueueDelayEntry 1 }

--5.7.8 Maximum Preemption Gates
maxPreemptGates OBJECT-TYPE
    SYNTAX Integer32 (1..255)
    UNITS "gate"
    MAX-ACCESS read-only
    STATUS current
    DESCRIPTION "<Definition> The maximum number of preempt gates this CU supports. This object indicates the maximum rows which shall appear in the preemptGateTable.
    <Object Identifier> 1.3.6.1.4.1.1206.4.2.1.6.8
    <Object Type> S"
    ::= { preempt 8 }

--5.7.9 Preempt Gate Table
preemptGateTable OBJECT-TYPE
    SYNTAX SEQUENCE OF PreemptGateEntry
    MAX-ACCESS not-accessible
    STATUS current
    DESCRIPTION "<Definition> A table containing the status of the gates that may be lowered during a preempt sequence.
    <TableType> static
    <Object Identifier> 1.3.6.1.4.1.1206.4.2.1.6.9"
    ::= { preempt 9 }

preemptGateEntry OBJECT-TYPE
    SYNTAX PreemptGateEntry
    MAX-ACCESS not-accessible
    STATUS current
    DESCRIPTION "<Definition> Gate status for preempt sequences.
    <Object Identifier> 1.3.6.1.4.1.1206.4.2.1.6.9.1"
    INDEX { preemptGateNumber }
    ::= { preemptGateTable 1 }

PreemptGateEntry ::= SEQUENCE {
    preemptGateNumber      INTEGER,
    preemptGateStatus      INTEGER,
    preemptGateDescription SnmpAdminString }

--5.7.9.1   Preempt Gate Number
preemptGateNumber OBJECT-TYPE
    SYNTAX Integer32 (1..255)
    MAX-ACCESS not-accessible
    STATUS current
    DESCRIPTION "<Definition> The Preempt Gate number for objects in this row.
    <Object Identifier> 1.3.6.1.4.1.1206.4.2.1.6.9.1.1"
    ::= { preemptGateEntry 1 }

--5.7.9.2   Preempt Gate Status
preemptGateStatus OBJECT-TYPE
    SYNTAX INTEGER { other(1),
                     unknown(2),
                     up(3),
                     down(4) }
    MAX-ACCESS read-only
    STATUS current
    DESCRIPTION "<Definition> The status of a gate that may be lowered during
        a preempt sequence.  
        unknown: The status of unknown or no gate is present
        other: The gate is neither in the locked up or locked down position
        up: The gate is in an up position
        down: The gate is in a down position
    <Object Identifier> 1.3.6.1.4.1.1206.4.2.1.6.9.1.2
    <Object Type> S"
    DEFVAL { 2 }
    ::= { preemptGateEntry 2 }

--5.7.9.3   Preempt Gate Description
preemptGateDescription OBJECT-TYPE
    SYNTAX SnmpAdminString 
    MAX-ACCESS read-write
    STATUS current
    DESCRIPTION "<Definition> A textual string indicate a user description for the gate (e.g. location).
    <Object Identifier> 1.3.6.1.4.1.1206.4.2.1.6.9.1.3
    <Object Type> P"
    ::= { preemptGateEntry 3 }

--5.8   Ring Parameters
ring  OBJECT IDENTIFIER
    ::= { asc  7 }

-- The ring node contains objects that support ring configuration, status and control functions in the device.

--5.8.1 Maximum Rings
maxRings OBJECT-TYPE
    SYNTAX Integer32 (1..255)
    UNITS "ring"
    MAX-ACCESS read-only
    STATUS current
    DESCRIPTION "<Definition> The value of this object shall specify the maximum number of rings this device supports.
    <Object Identifier> 1.3.6.1.4.1.1206.4.2.1.7.1
    <Object Type> S"
    ::= { ring 1 }

--5.8.2 Maximum Sequences
maxSequences OBJECT-TYPE
    SYNTAX Integer32 (1..255)
    UNITS "sequence"
    MAX-ACCESS read-only
    STATUS current
    DESCRIPTION "<Definition> The value of this object shall specify the maximum number of sequence plans this device supports.
    <Object Identifier> 1.3.6.1.4.1.1206.4.2.1.7.2
    <Object Type> S"
    ::= { ring 2 }

--5.8.3 Sequence Table
sequenceTable OBJECT-TYPE
    SYNTAX SEQUENCE OF SequenceEntry
    MAX-ACCESS not-accessible
    STATUS current
    DESCRIPTION "<Definition> This table contains all the sequence plans for the controller. A sequence plan shall consist of one row for each ring that the CU supports. Each row defines the phase service order for that ring.
    <TableType> static
    <Object Identifier> 1.3.6.1.4.1.1206.4.2.1.7.3"
    ::= { ring 3 }

sequenceEntry OBJECT-TYPE
    SYNTAX SequenceEntry
    MAX-ACCESS not-accessible
    STATUS current
    DESCRIPTION "<Definition> Phase Sequence Parameters for an Actuated Controller Unit.
    <Object Identifier> 1.3.6.1.4.1.1206.4.2.1.7.3.1"
    INDEX   { sequenceNumber, sequenceRingNumber }
    ::= { sequenceTable 1 }

SequenceEntry ::= SEQUENCE {
    sequenceNumber     Integer32,
    sequenceRingNumber Integer32,
    sequenceData       OCTET STRING }

--5.8.3.1   Sequence Number
sequenceNumber OBJECT-TYPE
    SYNTAX Integer32 (1..255)
    UNITS "sequence"
    MAX-ACCESS not-accessible
    STATUS current
    DESCRIPTION "<Definition> This number identifies a sequence plan. Each row of the table contains the phase sequence for a ring. A sequence plan shall consist of one row for each ring that defines the phase sequences for that ring.
    <Object Identifier> 1.3.6.1.4.1.1206.4.2.1.7.3.1.1"
    ::= { sequenceEntry 1 }

--5.8.3.2   Sequence Ring Number
sequenceRingNumber OBJECT-TYPE
    SYNTAX Integer32 (1..255)
    UNITS "ring"
    MAX-ACCESS not-accessible
    STATUS current
    DESCRIPTION "<Definition> This number identifies the ring number this phase sequence applies to.
    <Object Identifier> 1.3.6.1.4.1.1206.4.2.1.7.3.1.2"
    ::= { sequenceEntry 2 }

--5.8.3.3   Sequence Data
sequenceData OBJECT-TYPE
    SYNTAX OCTET STRING
    MAX-ACCESS read-write
    STATUS current
    DESCRIPTION "<Definition> Each octet is a Phase Number (binary value) within the associated ring number. The phase number value shall not exceed the maxPhases object value. The order of phase numbers determines the phase sequence for the ring. The phase numbers shall not be ordered in a manner that would violate the Consistency Checks defined in Section 4.3.2. Additionally, this object does not specify where barriers are present in the ring - the presences of barriers is determined by phaseConcurrency.
    <Object Identifier> 1.3.6.1.4.1.1206.4.2.1.7.3.1.3
    <Object Type> P2"
    ::= { sequenceEntry 3 }

--5.8.4 Maximum Ring Control Groups
maxRingControlGroups OBJECT-TYPE
    SYNTAX Integer32 (1..32)
    UNITS "group"
    MAX-ACCESS read-only
    STATUS current
    DESCRIPTION "<Definition> The maximum number of Ring Control Groups (8 rings per group) this Actuated Controller Unit supports. This value is equal to TRUNCATE [(maxRings + 7) / 8]. This object indicates the maximum rows which shall appear in the ringControlGroupTable object.
    <Object Identifier> 1.3.6.1.4.1.1206.4.2.1.7.4
    <Object Type> S"
    ::= { ring 4 }
 
--5.8.5 Ring Control Group Table
ringControlGroupTable OBJECT-TYPE
    SYNTAX SEQUENCE OF RingControlGroupEntry
    MAX-ACCESS not-accessible
    STATUS current
    DESCRIPTION "<Definition> A table containing Actuated Controller Unit Ring Control in groups of eight rings. The number of rows in this table is equal to the maxRingControlGroups object.
    <TableType> static
    <<Object Identifier> 1.3.6.1.4.1.1206.4.2.1.7.5"
    ::= { ring 5 }

ringControlGroupEntry OBJECT-TYPE
    SYNTAX RingControlGroupEntry
    MAX-ACCESS not-accessible
    STATUS current
    DESCRIPTION "<Definition> Ring Control for eight Actuated Controller Unit rings.
    <Object Identifier> 1.3.6.1.4.1.1206.4.2.1.7.5.1"
    INDEX   { ringControlGroupNumber }
    ::= { ringControlGroupTable 1 }

RingControlGroupEntry ::= SEQUENCE { 
    ringControlGroupNumber       Integer32,
    ringControlGroupStopTime     Integer32,
    ringControlGroupForceOff     Integer32,
    ringControlGroupMax2         Integer32,
    ringControlGroupMaxInhibit   Integer32,
    ringControlGroupPedRecycle   Integer32,
    ringControlGroupRedRest      Integer32,
    ringControlGroupOmitRedClear Integer32,
    ringControlGroupMax3         Integer32 }

--5.8.5.1   Ring Control Group Number
ringControlGroupNumber OBJECT-TYPE
    SYNTAX Integer32 (1..32)
    UNITS "group"
    MAX-ACCESS not-accessible
    STATUS current
    DESCRIPTION "<Definition> The Ring Control Group number for objects in this row. This value shall not exceed the maxRingControlGroups object value.
    <Object Identifier> 1.3.6.1.4.1.1206.4.2.1.7.5.1.1"
    ::= { ringControlGroupEntry 1 }
 
--5.8.5.2   Ring Stop Time Control
ringControlGroupStopTime OBJECT-TYPE
    SYNTAX Integer32 (0..255)
    MAX-ACCESS read-write
    STATUS current
    DESCRIPTION "<Definition> This object is used to allow a remote entity to stop timing in the device. The device shall activate/deactivate the System Stop Time control for a ring according to the respective bit value as follows:
bit = 0 - deactivate the ring control
bit = 1 - activate the ring control
Bit 7: Ring # = (ringControlGroupNumber * 8)
Bit 6: Ring # = (ringControlGroupNumber * 8) - 1
Bit 5: Ring # = (ringControlGroupNumber * 8) - 2
Bit 4: Ring # = (ringControlGroupNumber * 8) - 3
Bit 3: Ring # = (ringControlGroupNumber * 8) - 4
Bit 2: Ring # = (ringControlGroupNumber * 8) - 5
Bit 1: Ring # = (ringControlGroupNumber * 8) - 6
Bit 0: Ring # = (ringControlGroupNumber * 8) - 7
The device shall reset this object to ZERO when in BACKUP Mode. A write to this object shall reset the Backup timer to ZERO (see unitBackupTime).
    <Object Identifier> 1.3.6.1.4.1.1206.4.2.1.7.5.1.2
    <Object Type> C"
    REFERENCE "NEMA TS 2 Clause 3.5.4.1.6"
    ::= { ringControlGroupEntry 2 }

--5.8.5.3   Ring Force Off Control
ringControlGroupForceOff OBJECT-TYPE
    SYNTAX Integer32 (0..255)
    MAX-ACCESS read-write
    STATUS current
    DESCRIPTION "<Definition> This object is used to allow a remote entity to terminate phases via a force off command in the device. The device shall activate/deactivate the System Force Off control for a ring according to the respective bit value as follows:
bit = 0 - deactivate the ring control
bit = 1 - activate the ring control
Bit 7: Ring # = (ringControlGroupNumber * 8)
Bit 6: Ring # = (ringControlGroupNumber * 8) - 1
Bit 5: Ring # = (ringControlGroupNumber * 8) - 2
Bit 4: Ring # = (ringControlGroupNumber * 8) - 3
Bit 3: Ring # = (ringControlGroupNumber * 8) - 4
Bit 2: Ring # = (ringControlGroupNumber * 8) - 5
Bit 1: Ring # = (ringControlGroupNumber * 8) - 6
Bit 0: Ring # = (ringControlGroupNumber * 8) - 7
The device shall reset this object to ZERO when in BACKUP Mode. A write to this object shall reset the Backup timer to ZERO (see unitBackupTime).
    <Object Identifier> 1.3.6.1.4.1.1206.4.2.1.7.5.1.3
    <Object Type> C"
    REFERENCE "NEMA TS 2 Clause 3.5.4.1.1"
    ::= { ringControlGroupEntry 3 }

--5.8.5.4   Ring Max 2 Control
ringControlGroupMax2 OBJECT-TYPE
    SYNTAX Integer32 (0..255)
    MAX-ACCESS read-write
    STATUS current
    DESCRIPTION "<Definition> This object is used to allow a remote entity to request Maximum 2 timings in the device. The device shall activate/deactivate the System Maximum 2 control for a ring according to the respective bit value as follows:
bit = 0 - deactivate the ring control
bit = 1 - activate the ring control
Bit 7: Ring # = (ringControlGroupNumber * 8)
Bit 6: Ring # = (ringControlGroupNumber * 8) - 1
Bit 5: Ring # = (ringControlGroupNumber * 8) - 2
Bit 4: Ring # = (ringControlGroupNumber * 8) - 3
Bit 3: Ring # = (ringControlGroupNumber * 8) - 4
Bit 2: Ring # = (ringControlGroupNumber * 8) - 5
Bit 1: Ring # = (ringControlGroupNumber * 8) - 6
Bit 0: Ring # = (ringControlGroupNumber * 8) - 7
The device shall reset this object to ZERO when in BACKUP Mode. A write to this object shall reset the Backup timer to ZERO (see unitBackupTime).
    <Object Identifier> 1.3.6.1.4.1.1206.4.2.1.7.5.1.4
    <Object Type> C"
    REFERENCE "NEMA TS 2 Clause 3.5.4.1.7"
    ::= { ringControlGroupEntry 4 }

--5.8.5.5   Ring Max Inhibit Control
ringControlGroupMaxInhibit OBJECT-TYPE
    SYNTAX Integer32 (0..255)
    MAX-ACCESS read-write
    STATUS current
    DESCRIPTION
        "<Definition> This object is used to allow a remote entity to request
        internal maximum timings be inhibited in the device. The device shall
        activate/deactivate the System Max Inhibit control for a ring
        according to the respective bit value as follows:
            bit = 0 - deactivate the ring control
            bit = 1 - activate the ring control

        Bit 7: Ring # = (ringControlGroupNumber * 8)
        Bit 6: Ring # = (ringControlGroupNumber * 8) - 1
        Bit 5: Ring # = (ringControlGroupNumber * 8) - 2
        Bit 4: Ring # = (ringControlGroupNumber * 8) - 3
        Bit 3: Ring # = (ringControlGroupNumber * 8) - 4
        Bit 2: Ring # = (ringControlGroupNumber * 8) - 5
        Bit 1: Ring # = (ringControlGroupNumber * 8) - 6
        Bit 0: Ring # = (ringControlGroupNumber * 8) - 7

        The device shall reset this object to ZERO when in BACKUP Mode. A
        write to this object shall reset the Backup timer to ZERO (see
        unitBackupTime).
    <Object Identifier> 1.3.6.1.4.1.1206.4.2.1.7.5.1.5
    <Object Type> C"
    REFERENCE "NEMA TS 2 Clause 3.5.4.1.3"
    ::= { ringControlGroupEntry 5 }

--5.8.5.6   Ring Ped Recycle Control
ringControlGroupPedRecycle OBJECT-TYPE
    SYNTAX Integer32 (0..255)
    MAX-ACCESS read-write
    STATUS current
    DESCRIPTION "<Definition> This object is used to allow a remote entity to request a pedestrian recycle in the device. The device shall activate/deactivate the System Ped Recycle control for a ring according to the respective bit value as follows:
bit = 0 - deactivate the ring control
bit = 1 - activate the ring control
Bit 7: Ring # = (ringControlGroupNumber * 8)
Bit 6: Ring # = (ringControlGroupNumber * 8) - 1
Bit 5: Ring # = (ringControlGroupNumber * 8) - 2
Bit 4: Ring # = (ringControlGroupNumber * 8) - 3
Bit 3: Ring # = (ringControlGroupNumber * 8) - 4
Bit 2: Ring # = (ringControlGroupNumber * 8) - 5
Bit 1: Ring # = (ringControlGroupNumber * 8) - 6
Bit 0: Ring # = (ringControlGroupNumber * 8) - 7
The device shall reset this object to ZERO when in BACKUP Mode. A write to this object shall reset the Backup timer to ZERO (see unitBackupTime).
    <Object Identifier> 1.3.6.1.4.1.1206.4.2.1.7.5.1.6
    <Object Type> C"
    REFERENCE "NEMA TS 2 Clause 3.5.4.1.5"
    ::= { ringControlGroupEntry 6 }

--5.8.5.7   Ring Red Rest Control
ringControlGroupRedRest OBJECT-TYPE
    SYNTAX Integer32 (0..255)
    MAX-ACCESS read-write
    STATUS current
    DESCRIPTION "<Definition> This object is used to allow a remote entity to request red rest in the device. The device shall activate/deactivate the System Red Rest control for a ring according to the respective bit value as follows:
bit = 0 - deactivate the ring control
bit = 1 - activate the ring control
Bit 7: Ring # = (ringControlGroupNumber * 8)
Bit 6: Ring # = (ringControlGroupNumber * 8) - 1
Bit 5: Ring # = (ringControlGroupNumber * 8) - 2
Bit 4: Ring # = (ringControlGroupNumber * 8) - 3
Bit 3: Ring # = (ringControlGroupNumber * 8) - 4
Bit 2: Ring # = (ringControlGroupNumber * 8) - 5
Bit 1: Ring # = (ringControlGroupNumber * 8) - 6
Bit 0: Ring # = (ringControlGroupNumber * 8) - 7
The device shall reset this object to ZERO when in BACKUP Mode. A write to this object shall reset the Backup timer to ZERO (see unitBackupTime).
    <Object Identifier> 1.3.6.1.4.1.1206.4.2.1.7.5.1.7
    <Object Type> C"
    REFERENCE "NEMA TS 2 Clause 3.5.4.1.2"
    ::= { ringControlGroupEntry 7 }

--5.8.5.8   Ring Omit Red Control
ringControlGroupOmitRedClear OBJECT-TYPE
    SYNTAX Integer32 (0..255)
    MAX-ACCESS read-write
    STATUS current
    DESCRIPTION "<Definition> This object is used to allow a remote entity to omit red clearances in the device. The device shall activate/deactivate the System Omit Red Clear control for a ring according to the respective bit value as follows:
bit = 0 - deactivate the ring control
bit = 1 - activate the ring control
Bit 7: Ring # = (ringControlGroupNumber * 8)
Bit 6: Ring # = (ringControlGroupNumber * 8) - 1
Bit 5: Ring # = (ringControlGroupNumber * 8) - 2
Bit 4: Ring # = (ringControlGroupNumber * 8) - 3
Bit 3: Ring # = (ringControlGroupNumber * 8) - 4
Bit 2: Ring # = (ringControlGroupNumber * 8) - 5
Bit 1: Ring # = (ringControlGroupNumber * 8) - 6
Bit 0: Ring # = (ringControlGroupNumber * 8) - 7
The device shall reset this object to ZERO when in BACKUP Mode. A write to this object shall reset the Backup timer to ZERO (see unitBackupTime).
    <Object Identifier> 1.3.6.1.4.1.1206.4.2.1.7.5.1.8
    <Object Type> C"
    REFERENCE "NEMA TS 2 Clause 3.5.4.1.4"
    ::= { ringControlGroupEntry 8 }

--5.8.5.9   Ring Max 3 Control
ringControlGroupMax3 OBJECT-TYPE
    SYNTAX Integer32 (0..255)
    MAX-ACCESS read-write
    STATUS current
    DESCRIPTION "<Definition> This object is used to allow a remote entity to request Maximum 3 timings in the device. The device shall activate/deactivate the System Maximum 3 control for a ring according to the respective bit value as follows:
bit = 0 - deactivate the ring control
bit = 1 - activate the ring control
Bit 7: Ring # = (ringControlGroupNumber * 8)
Bit 6: Ring # = (ringControlGroupNumber * 8) - 1
Bit 5: Ring # = (ringControlGroupNumber * 8) - 2
Bit 4: Ring # = (ringControlGroupNumber * 8) - 3
Bit 3: Ring # = (ringControlGroupNumber * 8) - 4
Bit 2: Ring # = (ringControlGroupNumber * 8) - 5
Bit 1: Ring # = (ringControlGroupNumber * 8) - 6
Bit 0: Ring # = (ringControlGroupNumber * 8) - 7
The device shall reset this object to ZERO when in BACKUP Mode. 
A write to this object shall reset the Backup timer to ZERO (see unitBackupTime).
    <Object Identifier> 1.3.6.1.4.1.1206.4.2.1.7.5.1.9
    <Object Type> C"
    ::= { ringControlGroupEntry 9 }

--5.8.6 Ring Status Table
ringStatusTable OBJECT-TYPE
    SYNTAX SEQUENCE OF RingStatusEntry
    MAX-ACCESS not-accessible
    STATUS current
    DESCRIPTION "<Definition> A table containing Actuated Controller Unit Ring Status. The number of rows in this table is equal to the maxRings object.
    <TableType> static
    <Object Identifier> 1.3.6.1.4.1.1206.4.2.1.7.6"
    ::= { ring 6 }

ringStatusEntry OBJECT-TYPE
    SYNTAX RingStatusEntry
    MAX-ACCESS not-accessible
    STATUS current
    DESCRIPTION "<Definition> Ring Status for an Actuated Controller Unit ring.
    <Object Identifier> 1.3.6.1.4.1.1206.4.2.1.7.6.1"
    INDEX   { sequenceRingNumber }
    ::= { ringStatusTable 1 }

RingStatusEntry ::= SEQUENCE { 
    ringStatus          INTEGER,
    ringOnPhase         Integer32,
    ringOnPhaseDuration Unsigned32 }

--5.8.6.1   Ring Status
ringStatus OBJECT-TYPE
    SYNTAX Integer32 (0..65535)
    MAX-ACCESS read-only
    STATUS current
    DESCRIPTION "<Definition> The phase status for the phase indicated in the ringActivePhase object.
Bit 15: Reserved
Bit 14: Reserved
Bit 13: Reserved
Bit 12: Reserved
Bit 11: Don't Walk - When bit = 1, the active phase in the ring is currently displaying a steady DON'T WALK indication. 
Bit 10: Flashing Don't Walk - When bit = 1, the active phase in the ring is timing a pedestrian clearance interval and displaying a Flashing DON'T WALK indication.
Bit 9: Rest-in-Walk - When bit = 1, the active phase in the ring is currently resting in Walk when there is no serviceable conflicting call or because Max Vehicle Recall is enabled. 
Bit 8: Delayed Pedestrian Waiting - When bit = 1 the active phase in the ring has a delayed pedestrian interval and is currently displaying a vehicle GREEN indication before displaying WALK indication.
Bit 7: Walk - When bit = 1, the active phase in the ring is displaying a WALK indication.
Bit 6: Advanced Walk - When bit = 1, the active phase in the ring is timing a Leading Pedestrian Interval. 
Bit 5: Force Off - When bit = 1, the active phase in the ring was terminated by Force Off
Bit 4: Max Out - When bit = 1, the active phase in the ring was terminated by Max Out
Bit 3: Gap Out - When bit = 1, the active phase in the ring was terminated by Gap Out
Bit 2: Coded Status Bit C
Bit 1: Coded Status Bit B
Bit 0: Coded Status Bit A
+======+=====+=====+=====+===============+
| Code |    Bit States   | State         |
|  ##  |  A  |  B  |  C  | Names         |
+======+=====+=====+=====+===============+
|   0  |  0  |  0  |  0  | Min Green     |
|   1  |  1  |  0  |  0  | Extension     |
|   2  |  0  |  1  |  0  | Maximum |
|   3  |  1  |  1  |  0  | Green Rest    |
|   4  |  0  |  0  |  1  | Yellow Change |
|   5  |  1  |  0  |  1  | Red Clearance |
|   6  |  0  |  1  |  1  | Red Rest      |
|   7  |  1  |  1  |  1  | Undefined     |
+======+=====+=====+=====+===============+
NEMA TS 2 Clause 3.5.4.2 provides further definition of Coded Status Bits.
    <Object Identifier> 1.3.6.1.4.1.1206.4.2.1.7.6.1.1
    <Object Type> S"
    ::= { ringStatusEntry 1 }

--5.8.6.2   Ring On Phase
ringOnPhase OBJECT-TYPE
    SYNTAX Integer32 (0..255)
    UNITS "phase"
    MAX-ACCESS read-only
    STATUS current
    DESCRIPTION "<Definition> The phaseNumber of the phase in this ring that is currently on in a green, yellow, or red clearance interval. A value of zero indicates no phase is on for this ring. This value shall not exceed the value of maxPhases.
    <Object Identifier> 1.3.6.1.4.1.1206.4.2.1.7.6.1.2
    <Object Type> S"
    ::= { ringStatusEntry 2 }

--5.8.6.3   Ring On Phase Duration
ringOnPhaseDuration OBJECT-TYPE
    SYNTAX Unsigned32 (0..4294967295)
    UNITS "decisecond"
    MAX-ACCESS read-only
    STATUS current
    DESCRIPTION "<Definition> This value is the time, in tenth seconds, that the phase in ringOnPhase has been on since it began its vehicle GREEN (or WALK for leading pedestrian intervals) indication. This value shall reset to zero when the phase in ringOnPhase completes its red clearance interval. 
    <Object Identifier> 1.3.6.1.4.1.1206.4.2.1.7.6.1.3
    <Object Type> S"
    ::= { ringStatusEntry 3 }

--5.9   Channel Parameters
channel OBJECT IDENTIFIER 
    ::= { asc 8 }

--This defines a node for supporting channel objects.

--5.9.1 Maximum Channels
maxChannels OBJECT-TYPE
    SYNTAX Integer32 (1..255)
    UNITS   "channel"
    MAX-ACCESS read-only
    STATUS current
    DESCRIPTION "<Definition> The Maximum Number of Channels this Actuated Controller Unit supports. This object indicates the maximum rows which shall appear in the channel table.
    <Object Identifier> 1.3.6.1.4.1.1206.4.2.1.8.1
    <Object Type> S"
    ::= { channel 1 }

--5.9.2 Channel Table
channelTable OBJECT-TYPE
    SYNTAX SEQUENCE OF ChannelEntry
    MAX-ACCESS not-accessible
    STATUS current
    DESCRIPTION "<Definition> A table containing Actuated Controller Unit channel parameters. The number of rows in this table is equal to the maxChannels object.
    <TableType> static
    <Object Identifier> 1.3.6.1.4.1.1206.4.2.1.8.2"
    ::= { channel 2 }

channelEntry OBJECT-TYPE
    SYNTAX ChannelEntry
    MAX-ACCESS not-accessible
    STATUS current
    DESCRIPTION "<Definition> Parameters for a specific Actuated Controller Unit channel.
    <Object Identifier> 1.3.6.1.4.1.1206.4.2.1.8.2.1"
    INDEX   { channelNumber }
    ::= { channelTable 1 }

ChannelEntry ::= SEQUENCE { 
    channelNumber         Integer32,
    channelControlSource  Integer32,
    channelControlType    INTEGER,
    channelFlash          Integer32,
    channelDim            INTEGER, --deprecated
    channelGreenType      INTEGER, --deprecated
    channelGreenIncluded  OCTET STRING, --deprecated
    channelIntersectionId INTEGER --deprecated
    }

--5.9.2.1   Channel Number
channelNumber OBJECT-TYPE
    SYNTAX Integer32 (1..255)
    UNITS   "channel"
    MAX-ACCESS not-accessible
    STATUS current
    DESCRIPTION "<Definition> The channel number for objects in this row. This value shall not exceed the maxChannels object value.
    <Object Identifier> 1.3.6.1.4.1.1206.4.2.1.8.2.1.1"
    ::= { channelEntry 1 }

--5.9.2.2   Channel Control Source Parameter
channelControlSource OBJECT-TYPE
    SYNTAX Integer32 (0..255)
    MAX-ACCESS read-write
    STATUS current
    DESCRIPTION "<Definition> This object defines the channel control source (which Phase or Overlap). The value shall not exceed maxPhases or maxOverlaps as determined by channelControlType object:
Value 00 = No Control (Not in Use)
Value 01 = Phase 01 or Overlap A
Value 02 = Phase 02 or Overlap B
||
Value 15 = Phase 15 or Overlap O
Value 16 = Phase 16 or Overlap P
etc.
    <Object Identifier> 1.3.6.1.4.1.1206.4.2.1.8.2.1.2
    <Object Type> P2"
    ::= { channelEntry 2 }

--5.9.2.3   Channel Control Type Parameter
channelControlType OBJECT-TYPE
    SYNTAX INTEGER { other (1),
        phaseVehicle (2),
        phasePedestrian (3),
        overlap (4),
        pedOverlap (5),
        queueJump (6) }
    MAX-ACCESS read-write
    STATUS current
    DESCRIPTION "<Definition> This object defines the channel control type (Vehicle Phase, Pedestrian Phase, or Overlap):
other: The channel controls an other type of display.
phaseVehicle: The channel controls a vehicle phase display. Also valid for bicycle phases and transit phases.
phasePedestrian: The channel controls a pedestrian phase display.
overlap: The channel controls an overlap display, which might include flashing yellow arrows, flashing red arrows, vehicle overlaps, bicycle overlaps and transit overlaps.
pedOverlap: The channel controls an overlap for pedestrian display.
queueJump: The channel controls a queue jump display typically used for transit priority.
    <Object Identifier> 1.3.6.1.4.1.1206.4.2.1.8.2.1.3
    <Object Type> P2"
    ::= { channelEntry 3 }

--5.9.2.4   Channel Flash Parameter
channelFlash OBJECT-TYPE
    SYNTAX Integer32 (0..255)
    MAX-ACCESS read-write
    STATUS current
    DESCRIPTION "<Definition> This object defines the channel state during Automatic Flash. 
Bit 7: Reserved
Bit 6: Reserved
Bit 5: Reserved
Bit 4: Flash Alternate Second
Bit=0: Flash Alternate First (wig) & Bit=1: Flash Alternate Second (wag)
Bit 3: Flash Alternate Half Hertz
Bit=0: Off/Disabled & Bit=1: On/Enabled
Bit 2: Flash Red 
Bit=0: Off/Red Dark & Bit=1: On/Flash Red
Bit 1: Flash Yellow 
Bit=0: Off/Yellow Dark & Bit=1: On/Flash Yellow
Bit 0: Reserved
A SET of both bits 1 & 2 shall result in bit 1=0 and bit 2=1. 
A SET of a 'reserved' bit to a value other than zero shall return a badValue(3) error.
    <Object Identifier> 1.3.6.1.4.1.1206.4.2.1.8.2.1.4
    <Object Type> P"
    ::= { channelEntry 4 }

--5.9.2.5   Channel Dim Parameter
channelDim OBJECT-TYPE
    SYNTAX Integer32 (0..255)
    MAX-ACCESS read-write
    STATUS deprecated
    DESCRIPTION "<Definition> This object defines the channel state during Dimming. Dimming shall be accomplished by the elimination of alternate one-half segments from the AC sinusoid applied to the field terminals. 
Bit 7: Reserved
Bit 6: Reserved
Bit 5: Reserved
Bit 4: Reserved
Bit 3: Dim Alternate Half Line Cycle 
Bit=0: Off/+ half cycle & Bit=1: On/- half cycle
Bit 2: Dim Red 
Bit=0: Off/Red Not Dimmed & Bit=1: On/Dimmed Red
Bit 1: Dim Yellow 
Bit=0: Off / Yellow Not Dimmed & Bit=1: On / Dimmed Yellow
Bit 0: Dim Green 
Bit=0: Off / Green Not Dimmed & Bit=1: On / Dimmed Green
A SET of a 'reserved' bit to a value other than zero (0) shall return a badValue(3) error.
    <Object Identifier> 1.3.6.1.4.1.1206.4.2.1.8.2.1.5
    <Object Type> P"
    ::= { channelEntry 5 }

--5.9.2.6   Channel Movement Type
channelGreenType OBJECT-TYPE
    SYNTAX INTEGER { other (1),
    protected (2),
    permissive (3),
    flashYellow (4),
    flashRed (5) }
    MAX-ACCESS read-write
    STATUS deprecated
    DESCRIPTION "<Definition> This object defines the signalState for this channel when the channel output is Green. This object is used to support the generation of SPAT data.
other: the allowed movement controlled by this channel is not defined by this standard.
protected:   indicates that at least a portion of the green movement occurs in protected mode.
permissive: indicates that the green movement occurs in permissive mode, that is, any turns are permitted to be made only after yielding to pedestrians and/or any opposing traffic.
flashYellow: indicates that a vehicle may proceed but with caution after yielding to pedestrians and/or any conflicting traffic. Includes flashing yellow arrows.
flashRed: indicates that a vehicle may proceed after stopping and yielding to pedestrians and/or any conflicting traffic. Includes flashing red arrows.
Note that there is a similar object called movementManeuverGreenType.
    <Object Identifier> 1.3.6.1.4.1.1206.4.2.1.8.2.1.6
    <Object Type> P"
    ::= { channelEntry 6 }

--5.9.2.7   Channel Included Movements
channelGreenIncluded OBJECT-TYPE
    SYNTAX OCTET STRING
    MAX-ACCESS read-write
    STATUS deprecated
    DESCRIPTION "<Definition> If the channelGreenType for this channel is 'protected (2)', this object is used to indicate if and when this movement is in permissive mode. This object is used to support the generation of SPAT data and defines the signalState (See signalState) for the movements associated with this channel only IF the channelGreenType for this channel is 'protected (2)'. Each octet in the octet string represents a conflicting or opposing channelNumber, which if the status for any octet in the octet string is NOT Channel Red or is Dark, then the signalState for the movement is 'permissive-Movement-Allowed (5)' when the status for this channel is channel Green. Otherwise, the signalState for the movement is 'protected-Movement-Allowed (6)' when the status for this channel is channel Green.

    If channelGreenType in this row is not 'protected (2)', then this object value is ignored.

It is assumed that a clearance state following a signalState of 'permissive movement allowed' will be a signalState of 'permissive clearance', and a clearance state following a signalState of 'protected movement allowed' will be a signalState of 'protected movement allowed'.

For example, assume channelNumber 1 represents a northbound left turn, while channelNumber 2 is a southbound through movement. A channelGreenType.1 of 'protected (2)' and channelGreenIncluded.1 of '02' indicates that if the status of channelNumber 2 is NOT Channel Red or is dark, then signalState for the movement associated with channelNumber.1 is 'permissive-Movement-Allowed (5)' when the status for channelNumber.1 is channel Green. Otherwise, the signalState for the movement associated with channelNumber.1 is 'protected-Movement-Allowed (6)' when the status for this channel is channel Green.
    <Object Identifier> 1.3.6.1.4.1.1206.4.2.1.8.2.1.7
    <Object Type> P"
    ::= { channelEntry 7 }

--5.9.2.8   Channel Intersection Identifier
channelIntersectionId OBJECT-TYPE
    SYNTAX Integer32 (0..65535)
    MAX-ACCESS read-write
    STATUS deprecated
    DESCRIPTION "<Definition> To support SAE J2735, this object is used to support the exchange of SPAT data and contains the (regionally) unique identifier of the intersection that the channel output is associated with. It is expected that this same identifier will be broadcasted in a MAP data message that describes the roadway geometry configuration of this intersection.
    <Object Identifier> 1.3.6.1.4.1.1206.4.2.1.8.2.1.8
    <Object Type> P"
    REFERENCE "SAE J2735 DE_IntersectionID"
    ::= { channelEntry 8 }

--5.9.3 Maximum Channel Status Groups
maxChannelStatusGroups OBJECT-TYPE
    SYNTAX Integer32 (1..32)
    UNITS "group"
    MAX-ACCESS read-only
    STATUS current
    DESCRIPTION "<Definition> The maximum number of Channel Status Groups (8 channels per group) this Actuated Controller Unit supports. This value is equal to TRUNCATE [(maxChannels + 7) / 8]. This object indicates the maximum rows which shall appear in the channelStatusGroupTable object.
    <Object Identifier> 1.3.6.1.4.1.1206.4.2.1.8.3
    <Object Type> S"
    ::= { channel 3 }

--5.9.4 Channel Status Group Table
channelStatusGroupTable OBJECT-TYPE
    SYNTAX SEQUENCE OF ChannelStatusGroupEntry
    MAX-ACCESS not-accessible
    STATUS current
    DESCRIPTION "<Definition> A table containing Actuated Controller Unit channel output (Red, Yellow, & Green) status in groups of eight channels. The number of rows in this table is equal to the maxChannelStatusGroups object.
    <TableType> static
    <Object Identifier> 1.3.6.1.4.1.1206.4.2.1.8.4"
    ::= { channel 4 }

channelStatusGroupEntry OBJECT-TYPE
    SYNTAX ChannelStatusGroupEntry
    MAX-ACCESS not-accessible
    STATUS current
    DESCRIPTION "<Definition> Red, Yellow, & Green Output Status for eight Actuated Controller Unit channels.
    <Object Identifier> 1.3.6.1.4.1.1206.4.2.1.8.4.1"
    INDEX   { channelStatusGroupNumber }
    ::= { channelStatusGroupTable 1 }

ChannelStatusGroupEntry ::= SEQUENCE { 
    channelStatusGroupNumber  Integer32,
    channelStatusGroupReds    Integer32,
    channelStatusGroupYellows Integer32,
    channelStatusGroupGreens  Integer32 }

--5.9.4.1   Channel Status Group Number
channelStatusGroupNumber OBJECT-TYPE
    SYNTAX Integer32 (1..32)
    UNITS "group"
    MAX-ACCESS not-accessible
    STATUS current
    DESCRIPTION "<Definition> The channelStatusGroup number for objects in this row. This value shall not exceed the maxChannelStatusGroups object value.
    <Object Identifier> 1.3.6.1.4.1.1206.4.2.1.8.4.1.1"
    ::= { channelStatusGroupEntry 1 }

--5.9.4.2   Channel Status Group Reds
channelStatusGroupReds OBJECT-TYPE
    SYNTAX Integer32 (0..255)
    MAX-ACCESS read-only
    STATUS current
    DESCRIPTION "<Definition> Channel Red Output Status Mask, when a bit=1, the Channel Red is currently active. When a bit=0, the Channel Red is NOT currently active.
Bit 7: Channel # = (channelStatusGroupNumber * 8)
Bit 6: Channel # = (channelStatusGroupNumber * 8) - 1
Bit 5: Channel # = (channelStatusGroupNumber * 8) - 2
Bit 4: Channel # = (channelStatusGroupNumber * 8) - 3
Bit 3: Channel # = (channelStatusGroupNumber * 8) - 4
Bit 2: Channel # = (channelStatusGroupNumber * 8) - 5
Bit 1: Channel # = (channelStatusGroupNumber * 8) - 6
Bit 0: Channel # = (channelStatusGroupNumber * 8) - 7
    <Object Identifier> 1.3.6.1.4.1.1206.4.2.1.8.4.1.2
    <Object Type> S"
    ::= { channelStatusGroupEntry 2 }

--5.9.4.3   Channel Status Group Yellows
channelStatusGroupYellows OBJECT-TYPE
    SYNTAX Integer32 (0..255)
    MAX-ACCESS read-only
    STATUS current
    DESCRIPTION "<Definition> Channel Yellow Output Status Mask, when a bit=1, the Channel Yellow is currently active. When a bit=0, the Channel Yellow is NOT currently active.
Bit 7: Channel # = (channelStatusGroupNumber * 8)
Bit 6: Channel # = (channelStatusGroupNumber * 8) - 1
Bit 5: Channel # = (channelStatusGroupNumber * 8) - 2
Bit 4: Channel # = (channelStatusGroupNumber * 8) - 3
Bit 3: Channel # = (channelStatusGroupNumber * 8) - 4
Bit 2: Channel # = (channelStatusGroupNumber * 8) - 5
Bit 1: Channel # = (channelStatusGroupNumber * 8) - 6
Bit 0: Channel # = (channelStatusGroupNumber * 8) - 7
    <Object Identifier> 1.3.6.1.4.1.1206.4.2.1.8.4.1.3
    <Object Type> S"
    ::= { channelStatusGroupEntry 3 }

--5.9.4.4   Channel Status Group Greens
channelStatusGroupGreens OBJECT-TYPE
    SYNTAX Integer32 (0..255)
    MAX-ACCESS read-only
    STATUS current
    DESCRIPTION "<Definition> Channel Green Output Status Mask, when a bit=1, the Channel Green is currently active. When a bit=0, the Channel Green is NOT currently active.
Bit 7: Channel # = (channelStatusGroupNumber * 8)
Bit 6: Channel # = (channelStatusGroupNumber * 8) - 1
Bit 5: Channel # = (channelStatusGroupNumber * 8) - 2
Bit 4: Channel # = (channelStatusGroupNumber * 8) - 3
Bit 3: Channel # = (channelStatusGroupNumber * 8) - 4
Bit 2: Channel # = (channelStatusGroupNumber * 8) - 5
Bit 1: Channel # = (channelStatusGroupNumber * 8) - 6
Bit 0: Channel # = (channelStatusGroupNumber * 8) - 7
    <Object Identifier> 1.3.6.1.4.1.1206.4.2.1.8.4.1.4
    <Object Type> S"
    ::= { channelStatusGroupEntry 4 }

--5.10  Overlap Parameters
overlap   OBJECT IDENTIFIER
    ::= { asc 9 }

-- This node contains objects that configure, monitor and control overlap functions.

--5.10.1    Maximum Overlaps
maxOverlaps OBJECT-TYPE
    SYNTAX Integer32 (1..255)
    UNITS "overlap"
    MAX-ACCESS read-only
    STATUS current
    DESCRIPTION "<Definition> The Maximum Number of Overlaps this Actuated
        Controller Unit supports. This object indicates the maximum number of
        rows which shall appear in the overlapTable object.
    <Object Identifier> 1.3.6.1.4.1.1206.4.2.1.9.1
    <Object Type> S"
    ::= { overlap 1 }

--5.10.2    Overlap Table
overlapTable OBJECT-TYPE
    SYNTAX SEQUENCE OF OverlapEntry
    MAX-ACCESS not-accessible
    STATUS current
    DESCRIPTION "<Definition> A table containing Actuated Controller Unit
        overlap parameters. The number of rows in this table is equal to the
        maxOverlaps object.
    <TableType> static
    <Object Identifier> 1.3.6.1.4.1.1206.4.2.1.9.2"
    ::= { overlap 2 }

overlapEntry OBJECT-TYPE
    SYNTAX OverlapEntry
    MAX-ACCESS not-accessible
    STATUS current
    DESCRIPTION "<Definition> Parameters for a specific Actuated Controller
        Unit overlap.
    <Object Identifier> 1.3.6.1.4.1.1206.4.2.1.9.2.1"
    INDEX { overlapNumber }
    ::= { overlapTable 1 }

OverlapEntry ::= SEQUENCE { 
    overlapNumber               Integer32,
    overlapType                 INTEGER,
    overlapIncludedPhases       OCTET STRING,
    overlapModifierPhases       OCTET STRING,
    overlapTrailGreen           Integer32,
    overlapTrailYellow          Integer32,
    overlapTrailRed             Integer32,
    overlapWalk                 Integer32,
    overlapPedClearance         Integer32,
    overlapConflictingPedPhases OCTET STRING }

--5.10.2.1  Overlap Number
overlapNumber OBJECT-TYPE
    SYNTAX Integer32 (1..255)
    UNITS "overlap"
    MAX-ACCESS not-accessible
    STATUS current
    DESCRIPTION "<Definition> The overlap number for objects in this row. The
        value shall not exceed the maxOverlaps object. The value maps to the
        Overlap as follows: 
            1 = Overlap A, 2 = Overlap B etc.
    <Object Identifier> 1.3.6.1.4.1.1206.4.2.1.9.2.1.1
    <Object Type> S"
    ::= { overlapEntry 1 }
 
--5.10.2.2  Overlap Type
overlapType OBJECT-TYPE
    SYNTAX INTEGER { other(1),
                     normal (2),
                     minusGreenYellow (3),
                     pedestrianNormal (4),
                     fYAThreeSection (5),
                     fYAFourSection (6),
                     fRAThreeSection (7),
                     fRAFourSection (8),
                     transit-2 (9), 
                     minusGreenYellowAlternate (10)}
    MAX-ACCESS read-write
    STATUS current
    DESCRIPTION "<Definition> The type of overlap operation for this row. This value is the same for all overlap sets. The types are as follows:

        other: The overlap operates in another mode than those described herein.

        normal: The overlap output shall be controlled by the
            overlapIncludedPhases when this type is indicated. The overlap
            output shall be green in the following situations:
                (1) when an overlap included phase is green.
                (2) when an overlap included phase is yellow (or red clearance)
                    and an overlap included phase is next.
            The overlap output shall be yellow when an included phase is
            yellow and an overlap included phase is not next. The overlap
            output shall be red whenever the overlap green and yellow are
            not ON.

        minusGreenYellow: The overlap output shall be controlled by the
            overlapIncludedPhases and the overlapModifierPhases if this type
            is indicated. The overlap output shall be green in the following
            situations:
            (1) when an overlap included phase is green and an overlap
                modifier phase is NOT green.
            (2) when an overlap included phase is yellow (or red clearance)
                and an overlap included phase is next and an overlap modifier
                phase is NOT green.
            The overlap output shall be yellow when an overlap included phase
            is yellow and an overlap modifier phase is NOT yellow and an
            overlap included phase is not next. The overlap output shall be
            red whenever the overlap green and yellow are not ON.

        pedestrianNormal: The overlap output shall be controlled by the
            overlapIncludedPhases when this type is indicated. The overlap
            output shall be Walk in the following situations:
            (1) when an overlap included phase is in a walk interval. 
            (2) when an overlap included phase is in a pedestrian clearance
                    interval and an overlap included phase is next.
            Upon completion of the Walk interval, the overlap enters the
            pedestrian clearance interval if another included overlap phase is not next in the associated phase sequence. 
            The overlap output shall exit the pedestrian clearance interval to
            steady Dont Walk when the programmed pedestrian clearance time
            expires. The overlap output shall be steady Dont Walk whenever the
            overlap Walk and pedestrian clearance are not ON.

        fYAThreeSection: The overlap output shall be controlled by the
            overlapIncludedPhases and the overlapModifierPhases if this type
            is indicated. It shall be used with a 3-section signal head where
            the overlap output drives the green arrow, combined yellow/flashing
            yellow arrow, and red arrow. The permissive through phase opposing
            the left-turn signal is the overlapIncludedPhases and the
            associated left-turn protected phase is the overlapModifierPhases.
            The overlap output shall be FYA in the following situations:
            (1) when an overlap included phase is green and an overlap
                modifier phase is NOT green.
            (2) when an overlap included phase is yellow (or red clearance),
                an overlap included phase is next or an overlap modifier phase
                is next, and a modifier phase is NOT green.

            The overlap output shall be yellow:
                (1) when an overlap included phase is yellow, an overlap
                    included phase is not next, and an overlap modifier phase
                    is NOT green.
                (2) when an overlap modifier phase is yellow.

            The overlap output shall be red:
                (1) when an overlap included phase is red, an overlap modifier
                    phase is NOT green, and an overlap modifier phase is NOT
                    yellow.
                (2) when an overlap modifier phase is timing a red-clearance
                    interval.

            The overlap output shall be green:
                (1) when an overlap modifier phase is green.

        fYAFourSection: The overlap output shall be controlled by the
            overlapIncludedPhases and the overlapModifierPhases if this type
            is indicated. It shall be used with a 4-section signal head where
            the overlap output drives the flashing yellow arrow, yellow and
            red. The permissive through phase opposing the left-turn signal is
            the overlapIncludedPhases and the associated left-turn protected
            phase is the overlapModifierPhases.
            The overlap output shall be FYA in the following situations:
            (1) when an overlap included phase is green and an overlap
                modifier phase is NOT green.
            (2) when an overlap included phase is yellow (or red clearance),
                an overlap included phase or an overlap modifier phase is next
                and an overlap modifier phase is NOT green.

            The overlap output shall be yellow:
                (1) when an overlap included phase is yellow, an overlap
                    included phase is not next, and an overlap modifier phase
                    is NOT green.
                (2) when an overlap modifier phase is yellow.

            The overlap output shall be red:
                (1) when an overlap included phase is red, an overlap modifier
                    phase is NOT green, and an overlap modifier phase is NOT
                    yellow.
                (2) when an overlap modifier phase is timing a red-clearance
                    interval.

            The overlap output shall be blank/dark:
                (1) when an overlap modifier phase is green

        fRAThreeSection: The overlap output shall be controlled by the
            overlapIncludedPhases and the overlapModifierPhases if this type
            is indicated. The overlap output drives the green arrow, yellow
            arrow, and combined red/flashing red arrow. The
            overlapIncludedPhases is an opposing through phase and the
            overlapModifierPhases is a protected left turn phase.

            The overlap output shall be green when an overlap modifier phase
            is green.

            The overlap output shall be yellow:
                (1) when an overlap modifier phase is yellow.
                (2) when an overlap modifier phase is red and an overlap
                    included phase is yellow.

            The overlap output shall be red when the overlap modifier and
                included phases are red.
            The overlap output shall be flashing red when an overlap included
                phase is green and an overlap modifier phase is red.

        fRAFourSection: The overlap output shall be controlled by the
            overlapIncludedPhases and the overlapModifierPhases if this type
            is indicated. The overlap output drives the yellow arrow, red
            arrow, and flashing red arrow. The overlapIncludedPhases is an
            opposing through phase and the overlapModifierPhases is a
            protected left turn phase.

            The overlap outputs shall be blank when the overlapModifierPhase is green.

            The overlap output shall be yellow:
                (1) when an overlap modifier phase is yellow.
                (2) when an overlap modifier phase is red and an overlap included phase is yellow.

            The overlap output shall be red when an overlap modifier phase and
            an overlap included phase are red.
            The overlap output shall be flashing red when an overlap included
            phase is green and an overlap modifier phase is red.

        transit-2: The overlap output shall be controlled by the
            overlapIncludedPhases when this type is indicated. The overlap
            output drives a 2-section bar signal for transit vehicles using
            overlap green (vertical bar) and red (horizontal bar) outputs.

            The overlap output shall be green in the following situations:
                (1) when an overlap included phase is green.

            The overlap output shall be flashing green when an overlap
            included phase is yellow and an overlap included phase is not next.

            The overlap output shall be red whenever an overlap included phase
            is red.

        minusGreenYellowAlternate: The overlap output shall be controlled by
            the overlapIncludedPhases and the overlapModifierPhases if this
            type is indicated. The overlap output shall be green in the
            following situations:
                (1) when an overlap included phase is green and an overlap
                    modifier phase is NOT green.
                (2) when an overlap included phase is yellow (or red
                    clearance) and an overlap included phase is next and an
                    overlap modifier phase is NOT green and an overlap
                    modifier phase is not next.
      
            The overlap output shall be yellow when an overlap included phase
            is yellow and an overlap modifier phase is NOT yellow and an
            overlap included phase is not next. The overlap output shall be
            red whenever the overlap green and yellow are not ON.

        Note: Each enumeration requires the user to understand and avoid
        violation of MUTCD operational guidelines.
    <Object Identifier> 1.3.6.1.4.1.1206.4.2.1.9.2.1.2
    <Object Type> P2"
    DEFVAL {2}
    ::= { overlapEntry 2 }

--5.10.2.3  Overlap Included Phase Parameter
overlapIncludedPhases OBJECT-TYPE
    SYNTAX OCTET STRING
    MAX-ACCESS read-write
    STATUS current
    DESCRIPTION "<Definition> Each octet is a Phase (number) that shall be an
        included phase for the overlap. The phase number value shall not
        exceed the maxPhases object value.
    <Object Identifier> 1.3.6.1.4.1.1206.4.2.1.9.2.1.3
    <Object Type> P2"
    ::= { overlapEntry 3 }

--5.10.2.4  Overlap Modifier Phase Parameter
overlapModifierPhases OBJECT-TYPE
    SYNTAX OCTET STRING
    MAX-ACCESS read-write
    STATUS current
    DESCRIPTION "<Definition> Each octet is a Phase (number) that shall be a
        modifier phase for the overlap. The phase number value shall not
        exceed the maxPhases object value. The use of this object is defined
        by the overlapType. 
    <Object Identifier> 1.3.6.1.4.1.1206.4.2.1.9.2.1.4
    <Object Type> P2"
    ::= { overlapEntry 4 }

--5.10.2.5  Overlap Trailing Green Parameter
overlapTrailGreen OBJECT-TYPE
    SYNTAX Integer32 (0..255)
    UNITS "second"
    MAX-ACCESS read-write
    STATUS current
    DESCRIPTION "<Definition> Overlap Trailing Green Parameter in seconds
        (0-255 sec). When this value is greater than zero and the overlap
        green (or walk) would normally terminate, the overlap green (or walk)
        shall be extended by this additional time. This is applicable to
        vehicle phases, bicycle phases, and transit phases.
    <Object Identifier> 1.3.6.1.4.1.1206.4.2.1.9.2.1.5
    <Object Type> P"
    ::= { overlapEntry 5 }
 
--5.10.2.6  Overlap Trailing Yellow Change Parameter
overlapTrailYellow OBJECT-TYPE
    SYNTAX Integer32 (0..255)
    UNITS "decisecond"
    MAX-ACCESS read-write
    STATUS current
    DESCRIPTION "<Definition> Overlap Trailing Yellow Change Parameter in
        tenth seconds (NEMA range: 3.0-25.5 sec). When the overlap green has
        been extended (Trailing Green), this value shall determine the current
        length of the Yellow Change interval for the overlap. This is
        applicable to vehicle phases, bicycle phases, and transit phases.
    <Object Identifier> 1.3.6.1.4.1.1206.4.2.1.9.2.1.6
    <Object Type> P"
    ::= { overlapEntry 6 }

--5.10.2.7  Overlap Trailing Red Clearance Parameter
overlapTrailRed OBJECT-TYPE
    SYNTAX Integer32 (0..255)
    UNITS "decisecond"
    MAX-ACCESS read-write
    STATUS current
    DESCRIPTION "<Definition> Overlap Trailing Red Clearance Parameter in tenth
        seconds (0-25.5 sec). When the overlap green has been extended
        (Trailing Green), this value shall determine the current length of the
        Red Clearance interval for the overlap. This is applicable to vehicle
        phases, bicycle phases, and transit phases.
    <Object Identifier> 1.3.6.1.4.1.1206.4.2.1.9.2.1.7
    <Object Type> P"
    ::= { overlapEntry 7 }

--5.10.2.8  Overlap Walk Parameter
overlapWalk OBJECT-TYPE
    SYNTAX Integer32 (0..255)
    UNITS "second"
    MAX-ACCESS read-write
    STATUS current
    DESCRIPTION "<Definition> Overlap Walk Parameter in seconds (1-255 sec).
        This value is the length of the walk interval for a pedestrian
        overlap. Upon completion of the Walk interval, the overlap enters the
        pedestrian clearance interval. A value of zero indicates that the phaseWalk parameter of the currently running parent phase is used for this overlap.  
    <Object Identifier> 1.3.6.1.4.1.1206.4.2.1.9.2.1.8
    <Object Type> P"
    ::= { overlapEntry 8 }

--5.10.2.9  Overlap Pedestrian Clearance Parameter
overlapPedClearance OBJECT-TYPE
    SYNTAX Integer32 (0..255)
    UNITS "second"
    MAX-ACCESS read-write
    STATUS current
    DESCRIPTION "<Definition> Overlap Pedestrian Clearance Parameter in
        seconds (1-255 sec). This value is the length of the pedestrian
        clearance interval. A value of zero indicates that the phasePedestrianClear parameter of the currently running parent phase is used for this overlap
    <Object Identifier> 1.3.6.1.4.1.1206.4.2.1.9.2.1.9
    <Object Type> P"
    ::= { overlapEntry 9 }

--5.10.2.10 Overlap Conflicting Pedestrian Phase Parameter
overlapConflictingPedPhases OBJECT-TYPE
    SYNTAX OCTET STRING
    MAX-ACCESS read-write
    STATUS current
    DESCRIPTION "<Definition> Each octet is a Phase (number) that shall be a
        pedestrian modifier phase for the overlap. The phase number value
        shall not exceed the maxPhases object value.

        If the overlap type is 'normal', a non-null value would suppress the
        overlap when the pedestrian phase is active (in the walk or clearance
        interval). Upon completion of the active pedestrian phase and upon
        completion of a clearance interval (MUTCD requires 3 seconds), the
        overlap is allowed to proceed to the green state. 

        If the overlap type is fYAThreeSection or fYAFourSection, a non-null
        value would maintain the overlap red state when the pedestrian phase
        is active (in the walk or clearance interval). Upon completion of the
        active pedestrian phase and upon completion of a clearance interval
        (MUTCD requires 3 seconds), the overlap is allowed to proceed to the
        flashing yellow state. 
    <Object Identifier> 1.3.6.1.4.1.1206.4.2.1.9.2.1.10
    <Object Type> P2"
    ::= { overlapEntry 10 }

--5.10.3    Maximum Overlap Status Groups
maxOverlapStatusGroups OBJECT-TYPE
    SYNTAX Integer32 (1..32)
    UNITS "group"
    MAX-ACCESS read-only
    STATUS current
    DESCRIPTION "<Definition> The Maximum Number of Overlap Status Groups (8
        overlaps per group) this Actuated Controller Unit supports. This value
        is equal to TRUNCATE [(maxOverlaps + 7) / 8]. This object indicates
        the maximum rows which shall appear in the overlapStatusGroupTable
        object.
    <Object Identifier> 1.3.6.1.4.1.1206.4.2.1.9.3
    <Object Type> S"
    ::= { overlap 3 }
 
--5.10.4    Overlap Status Group Table
overlapStatusGroupTable OBJECT-TYPE
    SYNTAX SEQUENCE OF OverlapStatusGroupEntry
    MAX-ACCESS not-accessible
    STATUS current
    DESCRIPTION "<Definition> A table containing Actuated Controller Unit
        overlap output (Red, Yellow, & Green) status in groups of eight
        overlaps. The number of rows in this table is equal to the
        maxOverlapStatusGroups object.
    <TableType> static
    <Object Identifier> 1.3.6.1.4.1.1206.4.2.1.9.4"
    ::= { overlap 4 }

overlapStatusGroupEntry OBJECT-TYPE
    SYNTAX OverlapStatusGroupEntry
    MAX-ACCESS not-accessible
    STATUS current
    DESCRIPTION "<Definition> Red, Yellow, & Green Output Status for eight
        Actuated Controller Unit overlaps.
    <Object Identifier> 1.3.6.1.4.1.1206.4.2.1.9.4.1"
    INDEX   { overlapStatusGroupNumber }
    ::= { overlapStatusGroupTable 1 }

OverlapStatusGroupEntry ::= SEQUENCE { 
    overlapStatusGroupNumber  Integer32,
    overlapStatusGroupReds    Integer32,
    overlapStatusGroupYellows Integer32,
    overlapStatusGroupGreens  Integer32 }

--5.10.4.1  Overlap Status Group Number
overlapStatusGroupNumber OBJECT-TYPE
    SYNTAX Integer32 (1..32)
    UNITS "group"
    MAX-ACCESS not-accessible
    STATUS current
    DESCRIPTION "<Definition> The Overlap Status Group number for objects in
        this row. This value shall not exceed the maxOverlapStatusGroups
        object value.
    <Object Identifier> 1.3.6.1.4.1.1206.4.2.1.9.4.1.1
    <Object Type> S"
    ::= { overlapStatusGroupEntry 1 }
 
--5.10.4.2  Overlap Status Group Reds
overlapStatusGroupReds OBJECT-TYPE
    SYNTAX Integer32 (0..255)
    MAX-ACCESS read-only
    STATUS current
    DESCRIPTION "<Definition> Overlap Red Output Status Mask, when a bit=1,
        the Overlap Red is currently active. When a bit=0, the Overlap Red is
        NOT currently active.

        Bit 7: Overlap # = (overlapStatusGroupNumber * 8)
        Bit 6: Overlap # = (overlapStatusGroupNumber * 8) - 1
        Bit 5: Overlap # = (overlapStatusGroupNumber * 8) - 2
        Bit 4: Overlap # = (overlapStatusGroupNumber * 8) - 3
        Bit 3: Overlap # = (overlapStatusGroupNumber * 8) - 4
        Bit 2: Overlap # = (overlapStatusGroupNumber * 8) - 5
        Bit 1: Overlap # = (overlapStatusGroupNumber * 8) - 6
        Bit 0: Overlap # = (overlapStatusGroupNumber * 8) - 7
    <Object Identifier> 1.3.6.1.4.1.1206.4.2.1.9.4.1.2
    <Object Type> S"
    ::= { overlapStatusGroupEntry 2 }

--5.10.4.3  Overlap Status Group Yellows
overlapStatusGroupYellows OBJECT-TYPE
    SYNTAX Integer32 (0..255)
    MAX-ACCESS read-only
    STATUS current
    DESCRIPTION "<Definition> Overlap Yellow Output Status Mask, when a bit=1,
        the Overlap Yellow is currently active. When a bit=0, the Overlap
        Yellow is NOT currently active.

        Bit 7: Overlap # = (overlapStatusGroupNumber * 8)
        Bit 6: Overlap # = (overlapStatusGroupNumber * 8) - 1
        Bit 5: Overlap # = (overlapStatusGroupNumber * 8) - 2
        Bit 4: Overlap # = (overlapStatusGroupNumber * 8) - 3
        Bit 3: Overlap # = (overlapStatusGroupNumber * 8) - 4
        Bit 2: Overlap # = (overlapStatusGroupNumber * 8) - 5
        Bit 1: Overlap # = (overlapStatusGroupNumber * 8) - 6
        Bit 0: Overlap # = (overlapStatusGroupNumber * 8) - 7

        For pedestrianNormal overlap type, this object is used to represent
        the pedestrian clearance interval.
    <Object Identifier> 1.3.6.1.4.1.1206.4.2.1.9.4.1.3
    <Object Type> S"
    ::= { overlapStatusGroupEntry 3 }

--5.10.4.4  Overlap Status Group Greens
overlapStatusGroupGreens OBJECT-TYPE
    SYNTAX Integer32 (0..255)
    MAX-ACCESS read-only
    STATUS current
    DESCRIPTION "<Definition> Overlap Green Output Status Mask, when a bit=1,
        the Overlap Green is currently active. When a bit=0, the Overlap Green
        is NOT currently active.

        Bit 7: Overlap # = (overlapStatusGroupNumber * 8)
        Bit 6: Overlap # = (overlapStatusGroupNumber * 8) - 1
        Bit 5: Overlap # = (overlapStatusGroupNumber * 8) - 2
        Bit 4: Overlap # = (overlapStatusGroupNumber * 8) - 3
        Bit 3: Overlap # = (overlapStatusGroupNumber * 8) - 4
        Bit 2: Overlap # = (overlapStatusGroupNumber * 8) - 5
        Bit 1: Overlap # = (overlapStatusGroupNumber * 8) - 6
        Bit 0: Overlap # = (overlapStatusGroupNumber * 8) - 7
    <Object Identifier> 1.3.6.1.4.1.1206.4.2.1.9.4.1.4
    <Object Type> S"
    ::= { overlapStatusGroupEntry 4 }

--5.10.5    Maximum Overlap Sets
maxOverlapSets OBJECT-TYPE
    SYNTAX Integer32 (1..255)
    UNITS "set"
    MAX-ACCESS read-only
    STATUS current
    DESCRIPTION "<Definition> The Maximum Number of Overlap Sets this Actuated
        Controller Unit supports. This object indicates the maximum number of
        rows which shall appear in the overlapSetTable object.
    <Object Identifier> 1.3.6.1.4.1.1206.4.2.1.9.5
    <Object Type> S"
    ::= { overlap 5 }

--5.10.6    Overlap Set Table
overlapSetTable OBJECT-TYPE
    SYNTAX SEQUENCE OF OverlapSetEntry
    MAX-ACCESS not-accessible
    STATUS current
    DESCRIPTION "<Definition> A table containing Actuated Controller Unit
        overlap parameters. The number of rows in this table is equal to the
        maxOverlaps object.
    <TableType> static
    <Object Identifier> 1.3.6.1.4.1.1206.4.2.1.9.6"
    ::= { overlap 6 }

overlapSetEntry OBJECT-TYPE
    SYNTAX OverlapSetEntry
    MAX-ACCESS not-accessible
    STATUS current
    DESCRIPTION "<Definition> Parameters for a specific Actuated Controller
        Unit overlap.
    <Object Identifier> 1.3.6.1.4.1.1206.4.2.1.9.6.1"
    INDEX   { overlapSetNumber, overlapNumber }
    ::= { overlapSetTable 1 }

OverlapSetEntry ::= SEQUENCE { 
    overlapSetNumber                Integer32,
    overlapSetIncludedPhases       OCTET STRING,
    overlapSetModifierPhases       OCTET STRING,
    overlapSetTrailGreen           Integer32,
    overlapSetTrailYellow          Integer32,
    overlapSetTrailRed             Integer32,
    overlapSetWalk                 Integer32,
    overlapSetPedClearance         Integer32,
    overlapSetConflictingPedPhases OCTET STRING }

--5.10.6.1  Overlap Set Number
overlapSetNumber OBJECT-TYPE
    SYNTAX Integer32 (1..255)
    UNITS "overlap set"
    MAX-ACCESS not-accessible
    STATUS current
    DESCRIPTION "<Definition> The overlap number for objects in this row. The
        value shall not exceed the maxOverlapSets object. The value maps to the
        Overlap as follows: 
            1 = Overlap A, 2 = Overlap B etc.
    <Object Identifier> 1.3.6.1.4.1.1206.4.2.1.9.6.1.1
    <Object Type> S"
    ::= { overlapSetEntry 1 }

--Note: There is no parameter corresponding overlapType in overlapSetTable. 
 
--5.10.6.2  Overlap Set Included Phase Parameter
overlapSetIncludedPhases OBJECT-TYPE
    SYNTAX OCTET STRING
    MAX-ACCESS read-write
    STATUS current
    DESCRIPTION "<Definition> Each octet is a Phase (number) that shall be an
        included phase for the overlap. The phase number value shall not
        exceed the maxPhases object value.
    <Object Identifier> 1.3.6.1.4.1.1206.4.2.1.9.6.1.2
    <Object Type> P2"
    ::= { overlapSetEntry 2 }

--5.10.6.3  Overlap Set Modifier Phase Parameter
overlapSetModifierPhases OBJECT-TYPE
    SYNTAX OCTET STRING
    MAX-ACCESS read-write
    STATUS current
    DESCRIPTION "<Definition> Each octet is a Phase (number) that shall be a
        modifier phase for the overlap. The phase number value shall not
        exceed the maxPhases object value. The use of this object is defined
        by the overlapType. 
    <Object Identifier> 1.3.6.1.4.1.1206.4.2.1.9.6.1.3
    <Object Type> P2"
    ::= { overlapSetEntry 3 }

--5.10.6.4  Overlap Set Trailing Green Parameter
overlapSetTrailGreen OBJECT-TYPE
    SYNTAX Integer32 (0..255)
    UNITS "second"
    MAX-ACCESS read-write
    STATUS current
    DESCRIPTION "<Definition> Overlap Trailing Green Parameter in seconds
        (0-255 sec). When this value is greater than zero and the overlap
        green (or walk) would normally terminate, the overlap green (or walk)
        shall be extended by this additional time. This is applicable to
        vehicle phases, bicycle phases, and transit phases.
    <Object Identifier> 1.3.6.1.4.1.1206.4.2.1.9.6.1.4
    <Object Type> P"
    ::= { overlapSetEntry 4 }
 
--5.10.6.5  Overlap SetTrailing Yellow Change Parameter
overlapSetTrailYellow OBJECT-TYPE
    SYNTAX Integer32 (0..255)
    UNITS "decisecond"
    MAX-ACCESS read-write
    STATUS current
    DESCRIPTION "<Definition> Overlap Trailing Yellow Change Parameter in
        tenth seconds (NEMA range: 3.0-25.5 sec). When the overlap green has
        been extended (Trailing Green), this value shall determine the current
        length of the Yellow Change interval for the overlap. This is
        applicable to vehicle phases, bicycle phases, and transit phases.
    <Object Identifier> 1.3.6.1.4.1.1206.4.2.1.9.6.1.5
    <Object Type> P"
    ::= { overlapSetEntry 5 }

--5.10.6.6  Overlap Set Trailing Red Clearance Parameter
overlapSetTrailRed OBJECT-TYPE
    SYNTAX Integer32 (0..255)
    UNITS "decisecond"
    MAX-ACCESS read-write
    STATUS current
    DESCRIPTION "<Definition> Overlap Trailing Red Clearance Parameter in tenth
        seconds (0-25.5 sec). When the overlap green has been extended
        (Trailing Green), this value shall determine the current length of the
        Red Clearance interval for the overlap. This is applicable to vehicle
        phases, bicycle phases, and transit phases.
    <Object Identifier> 1.3.6.1.4.1.1206.4.2.1.9.6.1.6
    <Object Type> P"
    ::= { overlapSetEntry 6 }

--5.10.6.7  Overlap Set Walk Parameter
overlapSetWalk OBJECT-TYPE
    SYNTAX Integer32 (0..255)
    UNITS "second"
    MAX-ACCESS read-write
    STATUS current
    DESCRIPTION "<Definition> Overlap Walk Parameter in seconds (0-255 sec).
        This value is the length of the walk interval for a pedestrian
        overlap. Upon completion of the Walk interval, the overlap enters the
        pedestrian clearance interval.
    <Object Identifier> 1.3.6.1.4.1.1206.4.2.1.9.6.1.7
    <Object Type> P"
    ::= { overlapSetEntry 7 }

--5.10.6.8  Overlap Set Pedestrian Clearance Parameter
overlapSetPedClearance OBJECT-TYPE
    SYNTAX Integer32 (0..255)
    UNITS "second"
    MAX-ACCESS read-write
    STATUS current
    DESCRIPTION "<Definition> Overlap Pedestrian Clearance Parameter in
        seconds (0-255 sec). This value is the length of the pedestrian
        clearance interval.
    <Object Identifier> 1.3.6.1.4.1.1206.4.2.1.9.6.1.8
    <Object Type> P"
    ::= { overlapSetEntry 8 }

--5.10.6.9 Overlap Set Conflicting Pedestrian Phase Parameter
overlapSetConflictingPedPhases OBJECT-TYPE
    SYNTAX OCTET STRING
    MAX-ACCESS read-write
    STATUS current
    DESCRIPTION "<Definition> Each octet is a Phase (number) that shall be a
        pedestrian modifier phase for the overlap. The phase number value
        shall not exceed the maxPhases object value.

        If the overlap type is 'normal', a non-null value would suppress the
        overlap when the pedestrian phase is active (in the walk or clearance
        interval). Upon completion of the active pedestrian phase and upon
        completion of a clearance interval (MUTCD requires 3 seconds), the
        overlap is allowed to proceed to the green state. 

        If the overlap type is fYAThreeSection or fYAFourSection, a non-null
        value would maintain the overlap red state when the pedestrian phase
        is active (in the walk or clearance interval). Upon completion of the
        active pedestrian phase and upon completion of a clearance interval
        (MUTCD requires 3 seconds), the overlap is allowed to proceed to the
        flashing yellow state. 
    <Object Identifier> 1.3.6.1.4.1.1206.4.2.1.9.6.1.9
    <Object Type> P2"
    ::= { overlapSetEntry 9 }


--5.11  TS2 Port 1 Parameters
ts2port1  OBJECT IDENTIFIER
    ::= { asc 10 }

-- This object is an identifier used to group all objects for support of NEMA TS 2 (Clause 3.3.1) Port 1 activities.

--5.11.1    Maximum Port 1 Addresses
maxPort1Addresses OBJECT-TYPE
    SYNTAX Integer32 (1..255)
    UNITS "address"
    MAX-ACCESS read-only
    STATUS current
    DESCRIPTION "<Definition> The Maximum Number of Port 1 addresses this
        Actuated Controller Unit supports. This object indicates the maximum
        rows which shall appear in the port1Table object.
    <Object Identifier> 1.3.6.1.4.1.1206.4.2.1.10.1
    <Object Type> S"
    ::= { ts2port1 1 }

--5.11.2    Port 1 Table
port1Table OBJECT-TYPE
    SYNTAX SEQUENCE OF Port1Entry
    MAX-ACCESS not-accessible
    STATUS current
    DESCRIPTION "<Definition> A table containing Actuated Controller Unit
        port 1 parameters. The number of rows in this table is equal to
        maxPort1Addresses object. Address 255 is reserved for the all stations
        (link devices) address.
    <TableType> static
    <Object Identifier> 1.3.6.1.4.1.1206.4.2.1.10.2"
    ::= { ts2port1 2 }

port1Entry OBJECT-TYPE
    SYNTAX Port1Entry
    MAX-ACCESS not-accessible
    STATUS current
    DESCRIPTION "<Definition> This object defines a conceptual row in the
        port 1 Table.
    <Object Identifier> 1.3.6.1.4.1.1206.4.2.1.10.2.1"
    INDEX { port1Number }
    ::= { port1Table 1 }

Port1Entry ::= SEQUENCE {
    port1Number        Integer32,
    port1DevicePresent Integer32,
    port1Frame40Enable Integer32,
    port1Status        INTEGER,
    port1FaultFrame    Integer32 }

--5.11.2.1  Port 1 Number
port1Number OBJECT-TYPE
    SYNTAX Integer32 (1..255)
    UNITS "address"
    MAX-ACCESS not-accessible
    STATUS current
    DESCRIPTION "<Definition> The (Port 1 address plus one) for objects in
        this row. This value shall not exceed the maxPort1Addresses object
        value.
    <Object Identifier> 1.3.6.1.4.1.1206.4.2.1.10.2.1.1"
    ::= { port1Entry 1 }

--5.11.2.2  Port 1 Device Present
port1DevicePresent OBJECT-TYPE
    SYNTAX Integer32 (0..1)
    MAX-ACCESS read-write
    STATUS current
    DESCRIPTION "<Definition> This object is used to program the CU as to the
        presence or absence of a device for this Port 1 address. The CU shall
        transmit Command Frames only to those devices that are present as
        determined by this programming.
            True (one) - the device is present. 
            False (zero) - the device is not present.
    <Object Identifier> 1.3.6.1.4.1.1206.4.2.1.10.2.1.2
    <Object Type> P"
    REFERENCE "NEMA TS 2 Clause 3.3.1.4"
    ::= { port1Entry 2 }
 
--5.11.2.3  Port 1 Frame 40 Enable
port1Frame40Enable OBJECT-TYPE
    SYNTAX Integer32 (0..1)
    MAX-ACCESS read-write
    STATUS current
    DESCRIPTION "<Definition> To enable or disable Frame 40 messages to the
        device at this Port 1 address. Frame 40 is used to poll the secondary
        stations for a secondary to secondary message exchange. Command 40
        series frames shall be transmitted only to those devices that are
        enabled, as determined by this programming.
            TRUE (one) - Enable frame 40 messages for this device.
            FALSE (zero) - Disable frame 40 messages for this device.
    <Object Identifier> 1.3.6.1.4.1.1206.4.2.1.10.2.1.3
    <Object Type> P"
    REFERENCE "NEMA TS 2 Clause 3.3.1.4.1"
    ::= { port1Entry 3 }

--5.11.2.4  Port 1 Status
port1Status OBJECT-TYPE
    SYNTAX INTEGER { other (1),
                     online (2),
                     responseFault (3) }
    MAX-ACCESS read-only
    STATUS current
    DESCRIPTION "<Definition> This object indicates the communications status
        with the associated device:

        other: This indicates that some other communications fault has
            been detected.
        online: This indicates that at least five of the most recent 10
            response transfers were received correctly.
        responseFault: This indicates that more than 5 of the most recent 10
            response transfers were received incorrectly.
    <Object Identifier> 1.3.6.1.4.1.1206.4.2.1.10.2.1.4
    <Object Type> S"
    ::= { port1Entry 4 }

--5.11.2.5  Port 1 Fault Frame
port1FaultFrame OBJECT-TYPE
    SYNTAX Integer32 (0..255)
    MAX-ACCESS read-only
    STATUS current
    DESCRIPTION "<Definition> This object indicates the frame number that
        caused the most recent fault.
    <Object Identifier> 1.3.6.1.4.1.1206.4.2.1.10.2.1.5
    <Object Type> S"
    ::= { port1Entry 5 }

--5.12  ASC Block Objects
ascBlock  OBJECT IDENTIFIER
    ::= { asc 11 }

-- This object is an identifier used to group all objects for support of ASC Block Upload and Download activities.

--5.12.1    ASC Block Get Control
ascBlockGetControl OBJECT-TYPE
    SYNTAX OCTET STRING (SIZE(4..12))
    MAX-ACCESS read-write
    STATUS current
    DESCRIPTION "<Definition> An OER encoded string of reference parameters for ASC Block Uploads. The parameter values in this string are:

ascBlockDataType    INTEGER (0..255)
ascBlockDataID      INTEGER (0..255)
ascBlockIndex1      INTEGER (0..255) if needed
ascBlockQuantity1   INTEGER (0..255) if needed
ascBlockIndex2      INTEGER (0..255) if needed
ascBlockQuantity2   INTEGER (0..255) if needed
ascBlockIndex3      INTEGER (0..255) if needed
ascBlockQuantity3   INTEGER (0..255) if needed
ascBlockIndex4      INTEGER (0..255) if needed
ascBlockQuantity4   INTEGER (0..255) if needed
ascBlockIndex5      INTEGER (0..255) if needed
ascBlockQuantity5   INTEGER (0..255) if needed

A GET of ascBlockData shall utilize values currently in this object to define the data to be returned.

A SET of this object shall be evaluated for validity and Error Status of badValue(3) be returned for the following conditions:
1) ascBlockDataType is not supported
2) ascBlockDataID is not supported
3) ascBlockIndex1 is zero or not supported
4) ascBlockQuantity1 is zero or ascBlockIndex1 + ascBlockQuantity1 - 1 is not supported
5) ascBlockIndex2 is zero or not supported
6) ascBlockQuantity2 is zero or ascBlockIndex2 + ascBlockQuantity2) - 1 is not supported
7) ascBlockIndex3 is zero or not supported
8) ascBlockQuantity3 is zero or ascBlockIndex3 + scBlockQuantity3) - 1 is not supported
9) ascBlockIndex4 is zero or not supported
 
10) ascBlockQuantity4 is zero or ascBlockIndex4 + ascBlockQuantity4) - 1 is not supported
11) ascBlockIndex5 is zero or not supported
12) ascBlockQuantity5 is zero or ascBlockIndex5 + scBlockQuantity5) - 1 is not supported
13) if the SET length is zero or incorrect for ascBlockDataType & ascBlockDataID
14) if the GetResponse length for a GET on ascBlockData using maximum data field sizes would exceed a local limitation

When this validity check fails, ascBlockErrorStatus shall be set equal to the Bullet Value above that generated the error.
    <Object Identifier> 1.3.6.1.4.1.1206.4.2.1.11.1
    <Object Type> C"
    ::= { ascBlock 1 }

--5.12.2    ASC Block Data
ascBlockData OBJECT-TYPE
    SYNTAX OCTET STRING (SIZE(6..65535))
    MAX-ACCESS read-write
    STATUS current
    DESCRIPTION "<Definition> An OER encoded string used for uploading and downloading ASC parameters. See SECTION 6 for encoding and decoding the block. A SET on this object shall require the use of the Transaction feature defined in ISO 26048-1. 

A SET of this object shall be evaluated for validity and Error Status of badValue(3) be returned for the following conditions:
1) ascBlockDataType is not supported
2) ascBlockDataID is not supported
3) ascBlockIndex1 is zero or not supported
4) ascBlockQuantity1 is zero or ascBlockIndex1 + ascBlockQuantity1 - 1 is not supported
5) ascBlockIndex2 is zero or not supported
6) ascBlockQuantity2 is zero or ascBlockIndex2 + ascBlockQuantity2) - 1 is not supported
7) ascBlockIndex3 is zero or not supported
8) ascBlockQuantity3 is zero or ascBlockIndex3 + ascBlockQuantity3) - 1 is not supported
9) ascBlockIndex4 is zero or not supported
10) ascBlockQuantity4 is zero or ascBlockIndex4 + ascBlockQuantity4) - 1 is not supported
11) ascBlockIndex5 is zero or not supported
12) ascBlockQuantity5 is zero or ascBlockIndex5 + ascBlockQuantity5) - 1 is not supported
13) if the SET length is zero or incorrect for ascBlockDataType & ascBlockDataID
14) if the SET (SEQUENCE OF) value is incorrect.

When this validity check fails, ascBlockErrorStatus shall be set equal to the Bullet Value above that generated the error.

A SET that includes an unsupported value for a supported data element shall return an Error Status of badValue(3) and ascBlockErrorStatus shall be set equal to: (data Sequence # * 100) + data Element #

A SET that includes a non-zero or non-null value in the position of an unsupported data element shall return an Error Status of badValue(3) and ascBlockErrorStatus shall be set equal to: (data Sequence # * 100) + data Element #

A GET on this object shall utilize values currently in ascBlockGetControl to define the data to be returned. When ascBlockGetControl has invalid data, an Error STATUS of badValue(3) shall be returned.

A GET shall return a zero or null value in the position of an unsupported object.
    <Object Identifier> 1.3.6.1.4.1.1206.4.2.1.11.2
    <Object Type> C"
    ::= { ascBlock 2 }

--5.12.3    ASC Block Error Status
ascBlockErrorStatus OBJECT-TYPE
    SYNTAX Integer32 (0..65535)
    MAX-ACCESS read-only
    STATUS current
    DESCRIPTION "<Definition> This object defines the data element within ascBlockGetControl or ascBlockData that caused a badValue(3) ErrorStatus. This object should equal zero after any successful SET to ascBlockGetControl or ascBlockData.
    <Object Identifier> 1.3.6.1.4.1.1206.4.2.1.11.3
    <Object Type> S"
    ::= { ascBlock 3 }

--5.13  Cabinet Parameters
cabinetEnvironment  OBJECT IDENTIFIER --deprecated
    ::= { asc 12 }
-- This node contains objects that monitor and control the cabinet
-- environment functions for this device.

--5.13.1    Maximum Cabinet Environmental Monitoring Devices
maxCabinetEnvironDevices OBJECT-TYPE
    SYNTAX Integer32 (1..255)
    UNITS "device" -- number? v04 check
    MAX-ACCESS read-only
    STATUS deprecated
    DESCRIPTION "<Definition> The maximum number of environmental monitoring devices this CU supports. This object indicates the maximum rows which shall appear in the cabinetEnvironDevicesTable object.
    <Object Identifier> 1.3.6.1.4.1.1206.4.2.1.12.1
    <Object Type> S"
    ::= { cabinetEnvironment 1 }

--5.13.2    Cabinet Environmental Devices Table
cabinetEnvironDevicesTable OBJECT-TYPE
    SYNTAX SEQUENCE OF CabinetEnvironDevicesEntry
    MAX-ACCESS not-accessible
    STATUS deprecated
    DESCRIPTION "<Definition> A table containing the parameters of the environmental monitoring devices contained in the cabinet. The number of rows in this table is equal to the maxCabinetEnvironDevices object.
    <Object Identifier> 1.3.6.1.4.1.1206.4.2.1.12.2
    <TableType> static"
    ::= { cabinetEnvironment 2 }

cabinetEnvironDevicesEntry OBJECT-TYPE
    SYNTAX CabinetEnvironDevicesEntry
    MAX-ACCESS not-accessible
    STATUS deprecated
    DESCRIPTION "<Definition> Parameters for a specific CU cabinet environmental condition monitoring device.
    <Object Identifier> 1.3.6.1.4.1.1206.4.2.1.12.2.1"
    INDEX   { cabinetEnvironDeviceNumber, cabinetEnvironDeviceIndex }
    ::= { cabinetEnvironDevicesTable 1 }

CabinetEnvironDevicesEntry ::= SEQUENCE { 
    cabinetEnvironDeviceNumber      INTEGER, --deprecated
    cabinetEnvironDeviceType        INTEGER, --deprecated
    cabinetEnvironDeviceIndex       INTEGER, --deprecated
    cabinetEnvironDeviceDescription DisplayString, --deprecated
    cabinetEnvironDeviceOnStatus    INTEGER, --deprecated
    cabinetEnvironDeviceErrorStatus INTEGER } --deprecated

--5.13.2.1  Cabinet Environmental Monitoring Device Number
cabinetEnvironDeviceNumber OBJECT-TYPE
    SYNTAX Integer32 (1..255)
    UNITS "device"
    MAX-ACCESS not-accessible
    STATUS deprecated
    DESCRIPTION "<Definition> The environmental monitoring number for objects in this row. This value shall not exceed the maxCabinetEnvironDevices object value.
    <Object Identifier> 1.3.6.1.4.1.1206.4.2.1.12.2.1.1
    <Object Type> S"
    ::= { cabinetEnvironDevicesEntry 1 }

--5.13.2.2  Cabinet Environmental Monitoring Sensor Type
cabinetEnvironDeviceType OBJECT-TYPE
    SYNTAX INTEGER { other (1),
    door (2),
    fan (3),
    heater (4),
    floatSwitch (5)}
    MAX-ACCESS read-write
    STATUS deprecated
    DESCRIPTION "<Definition> The type of environment monitoring device to monitor the cabinet is an enumerated integer.
other: the type of environmental monitoring device is not defined by this standard.
door: this cabinet environmental monitoring device is a door to the cabinet.
fan: this cabinet environmental monitoring device is a fan within the cabinet.
heater: this cabinet environmental monitoring device is a heater within the cabinet.
floatSwitch: this cabinet environmental monitoring device is a float switch for water level detection.
    <Object Identifier> 1.3.6.1.4.1.1206.4.2.1.12.2.1.2
    <Object Type> P"
    ::= { cabinetEnvironDevicesEntry 2 }

--5.13.2.3  Cabinet Environmental Monitoring Device Index
cabinetEnvironDeviceIndex OBJECT-TYPE
    SYNTAX Integer32 (1..255)
    MAX-ACCESS not-accessible
    STATUS deprecated
    DESCRIPTION "<Definition> The index for the cabinetEnvironDeviceType. This value allows support for multiple sensors of a specific environment monitoring device type.
    <Object Identifier> 1.3.6.1.4.1.1206.4.2.1.12.2.1.3
    <Object Type> S"
    ::= { cabinetEnvironDevicesEntry 3 }

--5.13.2.4  Cabinet Environmental Monitoring Device Description
cabinetEnvironDeviceDescription OBJECT-TYPE
    SYNTAX DisplayString (SIZE (0..64))
    MAX-ACCESS read-write
    STATUS deprecated
    DESCRIPTION "<Definition> Human-readable description of the cabinet
        environmental device. This value should provide enough information for
        maintenance personnel to identify the type (door, fan, heater, etc.)
        and physical location of the device defined in this row within the CU
        or CU cabinet.
    <Object Identifier> 1.3.6.1.4.1.1206.4.2.1.12.2.1.4
    <Object Type> S"
    ::= { cabinetEnvironDevicesEntry 4 }

--5.13.2.5  Cabinet Environmental Monitoring Device On Status
cabinetEnvironDeviceOnStatus OBJECT-TYPE
    SYNTAX INTEGER { true (1),
                     false (2) }
    MAX-ACCESS read-only
    STATUS deprecated
    DESCRIPTION "<Definition> Indicates if this environmental monitoring
        device is on/open or off/closed. A bit orientation of 1 (true)
        indicates the environmental monitoring device is on, or in the case
        of a door, the door is open. A value of zero (false) indicates this
        environmental monitoring device is off, or in the case of a door, the
        door is closed.
    <Object Identifier> 1.3.6.1.4.1.1206.4.2.1.12.2.1.5
    <Object Type> S"
    ::= { cabinetEnvironDevicesEntry 5 }

--5.13.2.6  Cabinet Environmental Monitoring Device Error Status
cabinetEnvironDeviceErrorStatus OBJECT-TYPE
    SYNTAX INTEGER { other (1), --not used
                     noError (2),
                     fail (3),
                     notMonitored (4) }
    MAX-ACCESS read-only
    STATUS deprecated
    DESCRIPTION "<Definition> Indicates the current status of the
        environmental monitoring device.
    <Object Identifier> 1.3.6.1.4.1.1206.4.2.1.12.2.1.6
    <Object Type> S"
    ::= { cabinetEnvironDevicesEntry 6 }

--5.13.3    Maximum Number of Cabinet Temperature Sensors
maxCabinetTempSensors OBJECT-TYPE
    SYNTAX Integer32 (0..16)
    UNITS "temperature sensor" -- sensor? v04 check
    MAX-ACCESS read-only
    STATUS deprecated
    DESCRIPTION "<Definition> Indicates the number of rows in the cabinetTempSensorStatusTable. 
    <Object Identifier> 1.3.6.1.4.1.1206.4.2.1.12.3
    <Object Type> S"
    ::= { cabinetEnvironment 3 }

--5.13.4    Cabinet Temperature Sensor Status Table
cabinetTempSensorStatusTable OBJECT-TYPE
    SYNTAX SEQUENCE OF CabinetTempSensorStatusEntry 
    MAX-ACCESS not-accessible 
    STATUS deprecated 
    DESCRIPTION "<Definition> A table containing status information for each temperature sensor within a CU and CU cabinet. 
<Table Type> static 
    <Object Identifier> 1.3.6.1.4.1.1206.4.2.1.12.4"
    ::= { cabinetEnvironment 4 }

cabinetTempSensorStatusEntry OBJECT-TYPE 
    SYNTAX CabinetTempSensorStatusEntry 
    MAX-ACCESS not-accessible 
    STATUS deprecated
    DESCRIPTION "<Definition> An entry in the cabinet temperature sensor status table.
    <Object Identifier> 1.3.6.1.4.1.1206.4.2.1.12.4.1"
    INDEX { cabinetTempSensorIndex } 
    ::= { cabinetTempSensorStatusTable 1} 

CabinetTempSensorStatusEntry ::= SEQUENCE {
    cabinetTempSensorIndex          INTEGER, --deprecated
    cabinetTempSensorDescription    DisplayString, --deprecated
    cabinetTempSensorCurrentReading INTEGER, --deprecated
    cabinetTempSensorHighThreshold  INTEGER, --deprecated
    cabinetTempSensorLowThreshold   INTEGER, --deprecated
    cabinetTempSensorStatus         INTEGER } --deprecated

--5.13.4.1  Cabinet Temperature Sensor Index
cabinetTempSensorIndex OBJECT-TYPE
    SYNTAX Integer32 (1..16)
    MAX-ACCESS not-accessible
    STATUS deprecated
    DESCRIPTION "<Definition> Index of the cabinet temperature sensor status table. This value shall not exceed maxCabinetTempSensors.
    <Object Identifier> 1.3.6.1.4.1.1206.4.2.1.12.4.1.1
    <Object Type> S"
    ::= { cabinetTempSensorStatusEntry 1 }

--5.13.4.2  Cabinet Temperature Sensor Description
cabinetTempSensorDescription OBJECT-TYPE
    SYNTAX DisplayString (SIZE (0..64))
    MAX-ACCESS read-write
    STATUS deprecated
    DESCRIPTION "<Definition> Human-readable description of the temperature sensor. This value should provide enough information for maintenance personnel to identify the physical location of the temperature sensor within the CU or CU cabinet. 
    <Object Identifier> 1.3.6.1.4.1.1206.4.2.1.12.4.1.2
    <Object Type> S" 
    ::= { cabinetTempSensorStatusEntry 2 }

--5.13.4.3  Cabinet Temperature Sensor Current Reading 
cabinetTempSensorCurrentReading OBJECT-TYPE
    SYNTAX Integer32  (-128..127)
    UNITS "degree Celsius"
    MAX-ACCESS read-only
    STATUS deprecated
    DESCRIPTION "<Definition> Indicates the current reading, in degrees Celsius, of the temperature sensor.
<Valid Value Rule> The value -127 shall indicate a temperature of -127 degrees Celsius or lower. The value 127 shall indicate a temperature of 127 degrees Celsius or higher. The value -128 shall indicate an error condition or missing value.
    <Object Identifier> 1.3.6.1.4.1.1206.4.2.1.12.4.1.3
    <Object Type> S"
    DEFVAL { -56 }
    ::= { cabinetTempSensorStatusEntry 3 }

--5.13.4.4  Cabinet Temperature Sensor High Warning Temperature
cabinetTempSensorHighThreshold OBJECT-TYPE
    SYNTAX Integer32  (-128..127)
    UNITS "degree Celsius"
    MAX-ACCESS read-write
    STATUS deprecated
    DESCRIPTION "<Definition> Indicates the high value of the temperature, in degrees Celsius, associated with this temperature sensor above which would generate a warning (Bit 3 of unitAlarmStatus4). This value should not be lower than the value of the cabinetTempSensorLowThreshold object.
    <Object Identifier> 1.3.6.1.4.1.1206.4.2.1.12.4.1.4
    <Object Type> P"
    ::= { cabinetTempSensorStatusEntry 4 }

--5.13.4.5  Cabinet Temperature Sensor Low Warning Temperature
cabinetTempSensorLowThreshold OBJECT-TYPE
    SYNTAX Integer32 (-128..127)
    UNITS "degree Celsius"
    MAX-ACCESS read-write
    STATUS deprecated
    DESCRIPTION "<Definition> Indicates the low value of the temperature, in degrees Celsius, associated with this temperature sensor below which would generate a warning (Bit 3 of unitAlarmStatus4). This value should not be higher than the value of the cabinetTempSensorHighThreshold object.
    <Object Identifier> 1.3.6.1.4.1.1206.4.2.1.12.4.1.5
    <Object Type> P"
    ::= { cabinetTempSensorStatusEntry 5 }

--5.13.4.6  Cabinet Temperature Sensor Status 
cabinetTempSensorStatus OBJECT-TYPE
    SYNTAX INTEGER { other (1),
                     noError (2),
                     fail (3) }
    MAX-ACCESS read-only
    STATUS deprecated
    DESCRIPTION "<Definition> Indicates the current status of the indicated temperature sensor. 
    <Object Identifier> 1.3.6.1.4.1.1206.4.2.1.12.4.1.6
    <Object Type> P" 
    ::= { cabinetTempSensorStatusEntry 6 }

--5.13.5    Maximum Number of Humidity Sensors
maxCabinetHumiditySensors OBJECT-TYPE
    SYNTAX Integer32 (0..16)
    UNITS "humidity sensor"
    MAX-ACCESS read-only
    STATUS deprecated
    DESCRIPTION "<Definition> Indicates the number of rows in the cabinetHumiditySensorStatusTable.
    <Object Identifier> 1.3.6.1.4.1.1206.4.2.1.12.5
    <Object Type> P"
    ::= { cabinetEnvironment 5 }

--5.13.6    Cabinet Humidity Sensor Status Table
cabinetHumiditySensorStatusTable OBJECT-TYPE
    SYNTAX SEQUENCE OF CabinetHumiditySensorStatusEntry 
    MAX-ACCESS not-accessible 
    STATUS deprecated 
    DESCRIPTION "<Definition> A table containing status information for each humidity sensor within a CU cabinet. 
<Table Type> static 
    <Object Identifier> 1.3.6.1.4.1.1206.4.2.1.12.6" 
    ::= { cabinetEnvironment 6 }
 
cabinetHumiditySensorStatusEntry OBJECT-TYPE 
    SYNTAX CabinetHumiditySensorStatusEntry 
    MAX-ACCESS not-accessible 
    STATUS current 
    DESCRIPTION "<Definition> An entry in the humidity sensor status table. 
    <Object Identifier> 1.3.6.1.4.1.1206.4.2.1.12.6.1" 
    INDEX { cabinetHumiditySensorIndex } 
    ::= { cabinetHumiditySensorStatusTable 1} 

CabinetHumiditySensorStatusEntry ::= SEQUENCE {
    cabinetHumiditySensorIndex          INTEGER, --deprecated
    cabinetHumiditySensorDescription    DisplayString,--deprecated
    cabinetHumiditySensorCurrentReading INTEGER,--deprecated
    cabinetHumidityThreshold            INTEGER,--deprecated
    cabinetHumiditySensorStatus         INTEGER } --deprecated

--5.13.6.1  Cabinet Humidity Sensor Index
cabinetHumiditySensorIndex OBJECT-TYPE
    SYNTAX Integer32 (1..16)
    MAX-ACCESS not-accessible
    STATUS deprecated
    DESCRIPTION "<Definition> Index of the humidity sensor status table. This value does not exceed maxCabinetHumiditySensors.
    <Object Identifier> 1.3.6.1.4.1.1206.4.2.1.12.6.1.1
    <Object Type> S" 
    ::= { cabinetHumiditySensorStatusEntry 1 }

--5.13.6.2  Cabinet Humidity Sensor Description
cabinetHumiditySensorDescription OBJECT-TYPE
    SYNTAX DisplayString (SIZE (0..64))
    MAX-ACCESS read-write
    STATUS deprecated
    DESCRIPTION "<Definition> Human-readable description of the humidity sensor. This value should provide enough information for maintenance personnel to identify the physical location of the humidity sensor within the CU cabinet.
    <Object Identifier> 1.3.6.1.4.1.1206.4.2.1.12.6.1.2
    <Object Type> P" 
    ::= { cabinetHumiditySensorStatusEntry 2 }

--5.13.6.3  Cabinet Humidity Sensor Current Reading
cabinetHumiditySensorCurrentReading OBJECT-TYPE
    SYNTAX Integer32 (0..101)
    UNITS "percent relative humidity"
    MAX-ACCESS read-only
    STATUS deprecated
    DESCRIPTION "<Definition> Indicates the current reading of the humidity sensor, in percent relative humidity.
<Valid Value Rule> The value 101 shall indicate an error condition or missing value.
    <Object Identifier> 1.3.6.1.4.1.1206.4.2.1.12.6.1.3 
    <Object Type> S"
    DEFVAL { 101 }
    ::= { cabinetHumiditySensorStatusEntry 3 }

--5.13.6.4  Cabinet Humidity Sensor Threshold
cabinetHumidityThreshold OBJECT-TYPE
    SYNTAX Integer32 (0..101)
    UNITS "percent humidity"
    MAX-ACCESS read-write
    STATUS deprecated
    DESCRIPTION "<Definition> Indicates the relative humidity, in percent, within the CU cabinet above which the humidity threshold alarm shall be activated (Bit 3 of unitAlarmStatus4).
    <Object Identifier> 1.3.6.1.4.1.1206.4.2.1.12.6.1.4
    <Object Type> P"
    ::= { cabinetHumiditySensorStatusEntry 4 }

--5.13.6.5  Cabinet Humidity Sensor Status
cabinetHumiditySensorStatus OBJECT-TYPE
    SYNTAX INTEGER { other (1), --not used 
noError (2), 
fail (3) }
    MAX-ACCESS read-only
    STATUS deprecated
    DESCRIPTION "<Definition> Indicates the current status of the indicated humidity sensor.
    <Object Identifier> 1.3.6.1.4.1.1206.4.2.1.12.6.1.5
    <Object Type> S" 
    ::= { cabinetHumiditySensorStatusEntry 5 }

--5.13.7    Power Source
ascPowerSource OBJECT-TYPE
    SYNTAX INTEGER { unknown (1),
other (2),
acLine (3),
generator (4),
solar (5),
battery-UPS (6),
dc48VPower (7),
dc24Vpower (8) }   
    MAX-ACCESS read-only
    STATUS deprecated 
    DESCRIPTION "<Definition> Integer value that indicates the current primary power source for the CU cabinet, expressed as an enumerated integer.
unknown:    the current primary power source is unknown or cannot be determined.
other:  the current primary power source is not defined by this standard.
acLine: the current primary power source is in-line AC power.
generator:  the current primary power source is a generator that is operational.
solar: the current primary power source is solar equipment, that may be have a battery as an intermediary.
battery-UPS:    the current primary power source is a battery or UPS with no significant charging occurring.
dc48VPower: the current primary power source is 48 volts DC directly into the cabinet.
dc24VPower: the current primary power source is 48 volts DC directly into the cabinet.
    <Object Identifier> 1.3.6.1.4.1.1206.4.2.1.12.7
    <Object Type> S"
    DEFVAL  { unknown }
    ::= { cabinetEnvironment 7 }

--5.13.8    Line Volts
ascLineVolts OBJECT-TYPE
    SYNTAX Integer32 (0..6001)
    UNITS "0.1 Volts Root Mean Squared (Vrms)"
    MAX-ACCESS read-only 
    STATUS deprecated
    DESCRIPTION "<Definition> Indicates the voltage, in 0.1 RMS volt units, measured on the incoming power line for the CU. This object shall only be used to indicate A/C power conditions. If the line power is DC, this object shall not apply (i.e., this object will either not be supported or this object will have a value of 3001).
<Valid Value Rule> Values 0 through 5999 shall indicate valid values. The value 6000 shall mean a voltage of 600.0 Vrms or greater. The value of 6001 shall indicate an error condition or missing value.
    <Object Identifier> 1.3.6.1.4.1.1206.4.2.1.12.8
    <Object Type> S"
    DEFVAL  { 6001 }
    ::= { cabinetEnvironment 8 }

--5.13.9    ATC Cabinet LED Displays
atccLEDMode OBJECT-TYPE
    SYNTAX INTEGER { other (1),
on (2),
off (3) }
    MAX-ACCESS read-write
    STATUS deprecated 
    DESCRIPTION "<Definition> Object that allows control of the LED displays within an ATC cabinet.
other: LED mode of operation is not defined by this standard.
on: ATCC module LEDs operate normally (e.g., full brightness and flashing are prescribed by module documentation).
off: ATCC module LEDs are off (sleep) when all cabinet door(s) are closed.
All other values are RESERVED.
    <Object Identifier> 1.3.6.1.4.1.1206.4.2.1.12.9
    <Object Type> P"
    ::= { cabinetEnvironment 9 }

--5.13  I/O Mapping
ascIOmapping OBJECT IDENTIFIER
    ::= { asc 13 }

-- This node contains objects that configure, monitor or control input and output mapping in the ASC

--5.13.1    I/O Mapping Control
ascIOmapControl OBJECT IDENTIFIER
    ::= { ascIOmapping 1 }

-- This node contains objects that control the current I/O map

--5.13.1.1  Maximum Number of I/O Maps
ascIOmaxMaps OBJECT-TYPE
    SYNTAX Integer32 (1..255)
    MAX-ACCESS read-only
    STATUS current
    DESCRIPTION "<Definition> This object contains the maximum number of I/O maps this ASC supports. This object indicates the number of rows in the ascIOmapsTable.
    <Object Identifier> 1.3.6.1.4.1.1206.4.2.1.13.1.1
    <Object Type> S"
    ::= { ascIOmapControl 1 }

--5.13.1.2  Active I/O Map
ascIOactiveMap OBJECT-TYPE
    SYNTAX Integer32 (1..255)
    MAX-ACCESS read-write
    STATUS current
    DESCRIPTION "<Definition> This object selects the active I/O map. This object has to be changed using the Transaction feature defined in ISO 26048-1. A Database Transaction that changes this object or edits the currently active I/O map has to satisfy the activation requirements in ascIOactivateRequirement at the time fdTransactionMode is set to verify (3) for the transaction to successfully verify.

      The value of this object cannot exceed the value of ascIOmaxMaps.
    <Object Identifier> 1.3.6.1.4.1.1206.4.2.1.13.1.2
    <Object Type> S"
    DEFVAL { 1 }
    ::= { ascIOmapControl 2 }

--5.13.1.3  Conditions for Activating New I/O Map
ascIOactivateRequirement OBJECT-TYPE
    SYNTAX Integer32 (0..255)
    MAX-ACCESS read-only
    STATUS current
    DESCRIPTION "<Definition> This object returns the conditions under which an ASC will confirm a DB transaction that activates a new I/O map or edits the currently active I/O map. The requirements are selected in a bitmap format:
        Bit 0 - cabinetDoorOpen -- I/O input cabinetDoorOpen active
        Bit 1 - inFlash         -- in any flash state
        Bit 2 - allRedFlash     -- in programmed all red flash
        Bit 3 - cabinetFlash    -- in CVM flash, input localFlashSense active
        Bit 4 - restart         -- changes take effect only after a restart
        Bit 5 - reserved
        Bit 6 - reserved
        Bit 7 - reserved
    Note: if all I/O mapping values being set are the same as the   current values, the DB transaction shall succeed without requiring any conditions set by this object.
    <Object Identifier> 1.3.6.1.4.1.1206.4.2.1.13.1.3
    <Object Type> S"
    ::= { ascIOmapControl 3 }

--5.13.2    I/O Maps Maximum Inputs
ascIOmapMaxInputs OBJECT-TYPE
    SYNTAX Integer32 (1..65535)
    MAX-ACCESS read-only
    STATUS current
    DESCRIPTION "<Definition> This object contains the maximum number of I/O mapping input functions this ASC supports. This object indicates the number of rows in the ascIOinputMapTable.
    <Object Identifier> 1.3.6.1.4.1.1206.4.2.1.13.2
    <Object Type> S"
    ::= { ascIOmapping 2 }

--5.13.3    I/O Maps Maximum Outputs
ascIOmapMaxOutputs OBJECT-TYPE
    SYNTAX Integer32 (1..65535)
    MAX-ACCESS read-only
    STATUS current
    DESCRIPTION "<Definition> This object contains the maximum number of I/O mapping output functions this ASC supports. This object indicates the number of rows in the ascIOoutputMapTable.
    <Object Identifier> 1.3.6.1.4.1.1206.4.2.1.13.3
    <Object Type> S"
    ::= { ascIOmapping 3 }

--5.13.4    I/O Input Map Table
ascIOinputMapTable OBJECT-TYPE
    SYNTAX SEQUENCE OF AscIOinputMapTableEntry
    MAX-ACCESS not-accessible
    STATUS current
    DESCRIPTION "<Definition> A table containing mapping for an ASC Controller's inputs to functions. The number of I/O input map tables is equal to the value of ascIOmaxMaps.
      The total number of rows in the table is ascIOmapMaxInputs. Only one I/O input map may be active at any one time, and is selected by ascIOactiveMap.
    <TableType> static
    <Object Identifier> 1.3.6.1.4.1.1206.4.2.1.13.4"
    ::= { ascIOmapping 4 }

ascIOinputMapTableEntry OBJECT-TYPE
    SYNTAX AscIOinputMapTableEntry
    MAX-ACCESS not-accessible
    STATUS current
    DESCRIPTION "<Definition> This object defines a conceptual row in the ascIOinputMapTable.
    <Object Identifier> 1.3.6.1.4.1.1206.4.2.1.13.4.1"
    INDEX { ascIOmapNumber,  ascIOinputMapIOindex }
    ::= { ascIOinputMapTable 1 }

AscIOinputMapTableEntry ::= SEQUENCE {
   ascIOmapNumber           Integer32,   -- up to ascIOmaxMaps
   ascIOinputMapIOindex     Integer32,     -- up to ascIOmapMaxInputs
   ascIOinputMapDeviceType  INTEGER,   -- enum custom, FIO,TS1,BIU,SIU,AUX, reserved
   ascIOinputMapDevicePNN   Integer32,   -- NEMA PNN if DeviceType is custom
   ascIOinputMapDevicePtype Integer32,   -- Custom device type
   ascIOinputMapDeviceAddr  Integer32,   -- only used if needed (BIU, SIU)
   ascIOinputMapDevicePin   INTEGER,     -- device I/O pin index
   ascIOinputMapFuncType    Integer32,   -- 0=STD, else nemaPrivate vendor code
   ascIOinputMapFuncPtype   Integer32,   -- Custom function type set
   ascIOinputMapFunction    Integer32,   -- function 
   ascIOinputMapFuncIndex   Integer32 }  -- index if function support more than one input or output

--5.13.4.1  I/O Map Number
ascIOmapNumber OBJECT-TYPE
    SYNTAX Integer32 (1..255)
    MAX-ACCESS not-accessible
    STATUS current
    DESCRIPTION "<Definition> The value of this object shall not exceed the ascIOmaxMaps value.
    <Object Identifier> 1.3.6.1.4.1.1206.4.2.1.13.4.1.1
    <Object Type> S"
    ::= { ascIOinputMapTableEntry 1 }

--5.13.4.2  I/O Input Map Index
ascIOinputMapIOindex OBJECT-TYPE
    SYNTAX Integer32 (1..65535)
    MAX-ACCESS not-accessible
    STATUS current
    DESCRIPTION "<Definition> The I/O index for this row of the table. The range will not exceed ascIOmapMaxInputs.
    <Object Identifier> 1.3.6.1.4.1.1206.4.2.1.13.4.1.2
    <Object Type> S "
    ::= { ascIOinputMapTableEntry 2 }

--5.13.4.3  I/O Input Map Device Type
ascIOinputMapDeviceType OBJECT-TYPE
    SYNTAX INTEGER { unused (1),
                  custom (2),
                  fio (3),
                  ts1 (4),
                  biu (5),
                  siu (6),
                  aux (7) }
    MAX-ACCESS read-write
    STATUS current
    DESCRIPTION "<Definition> This object is an selects the device type for this row of the table.
      A value of unused (1) means that this row of the table is unused (all values of ascIOinputMapIOindex up to ascIOmapMaxInputs may not be needed by every mapping).

A custom type is a manufacturer defined device which also requires a ascIOinputMapDevicePNN and a ascIOinputMapDevicePtype to fully specify the device.

Values > 7 are reserved for future device types.
    <Object Identifier> 1.3.6.1.4.1.1206.4.2.1.13.4.1.3
    <Object Type> P"
    ::= { ascIOinputMapTableEntry 3 }

--5.13.4.4  I/O Input Map Custom Device Manufacturer ID
ascIOinputMapDevicePNN OBJECT-TYPE
 SYNTAX Integer32 (0..65535)
 MAX-ACCESS read-write
 STATUS current
 DESCRIPTION "<Definition> The object is used to further define a device type when ascIOinputMapDeviceType is custom (2). The value of this object will be the manufacturer's Private Node Number (PNN) as assigned by NEMA (1.3.6.1.4.1.1206.3.PNN). This is the same identifier used for ASC custom blocks.
    <Object Identifier> 1.3.6.1.4.1.1206.4.2.1.13.4.1.4
    <Object Type> P"
    ::= { ascIOinputMapTableEntry 4 }

--5.13.4.5  I/O Input Map Custom Device Type
ascIOinputMapDevicePtype OBJECT-TYPE
    SYNTAX Integer32 (0..255)
    MAX-ACCESS read-write
    STATUS current
    DESCRIPTION "<Definition> The object is used to further define a device type when ascIOinputMapDeviceType is custom (2). The value of this object will identify a custom device type unique to the manufacturer specified by ascIOinputMapDevicePNN.
    <Object Identifier> 1.3.6.1.4.1.1206.4.2.1.13.4.1.5
    <Object Type> P"
    ::= { ascIOinputMapTableEntry 5 }

--5.13.4.6  I/O Input Map Device Address
ascIOinputMapDeviceAddr OBJECT-TYPE
    SYNTAX Integer32 (0..255)
    MAX-ACCESS read-write
    STATUS current
    DESCRIPTION "<Definition> An address for the device at this table row. The address is used for devices like BIUs and SIUs that require an address. The value should be zero if the address is not needed for this row.
      If the ascIOinputMapDeviceType is biu (4), the address values are:
                1   - Traffic Facilities BIU #1
                2   - Traffic Facilities BIU #2
                3   - Traffic Facilities BIU #3
                4   - Traffic Facilities BIU #4
                5-8 - reserved
                9   - Detector BIU #1
                10  - Detector BIU #2
                11  - Detector BIU #3
                12  - Detector BIU #4
                13-16 - reserved
      Note that these values are the BIU SDLC address + 1.

      If the ascIOinputMapDeviceType is siu (5), the address values are:
                1  - reserved
                2  - 14-pack output SIU position 1
                3  - reserved
                4  - 14-pack output SIU position 3
                5  -  6-pack output SIU position 4
                6  -  6-pack output SIU position 1
                7  -  6-pack output SIU position 2
                8  -  6-pack output SIU position 3
                9  - reserved
                10 - input SIU #1
                11 - input SIU #2
                12 - input SIU #3
                13 - input SIU #4
                14 - input SIU #5
                15 - reserved
        Note that these values are the SIU SDLC address + 1.
    <Object Identifier> 1.3.6.1.4.1.1206.4.2.1.13.4.1.6
    <Object Type> P"
    ::= { ascIOinputMapTableEntry 6 }

--5.13.4.7  I/O Input Map Device Pin
ascIOinputMapDevicePin OBJECT-TYPE
    SYNTAX Integer32 (0..255)
    MAX-ACCESS read-write
    STATUS current
    DESCRIPTION "<Definition> An index for the I/O pin at this table row. The range for this value will depend upon the value of other objects in the row.
      The range for ascIOinputMapDeviceType:
            fio (3) pin range is AscIOmapFIOinputs
            ts1 (4) pin range is AscIOmapTS1inputs
            biu (5) pin range is AscIOmapBIUinputs
            siu (6) pin range is AscIOmapSIUinputs
            aux (7) pin range is AscIOmapAUXinputs
      The range for a custom device type will be determined by the manufacturer defining it.
    <Object Identifier> 1.3.6.1.4.1.1206.4.2.1.13.4.1.7
    <Object Type> P"
    ::= { ascIOinputMapTableEntry 7 }

--5.13.4.8  I/O Input Map Function Type
ascIOinputMapFuncType OBJECT-TYPE
    SYNTAX Integer32 (0..65535)
    MAX-ACCESS read-write
    STATUS current
    DESCRIPTION "<Definition> This object selects the function type for this row of the table. A value of zero references the standard input functions defined by AscIOinputType and the ascIOinputMapFunction.
      Any other value is a manufacturer's Private Node Number (PNN) as assigned by NEMA (1.3.6.1.4.1.1206.3.PNN). In this case the  function is defined by the PNN (the manufacturer), ascIOinputMapFuncPtype (which of the manufacturer's multiple function sets), and the ascIOinputMapFunction.
    <Object Identifier> 1.3.6.1.4.1.1206.4.2.1.13.4.1.8
    <Object Type> P"
    ::= { ascIOinputMapTableEntry 8 }

--5.13.4.9  I/O Input Map Custom Function Type
ascIOinputMapFuncPtype OBJECT-TYPE
    SYNTAX Integer32 (0..255)
    MAX-ACCESS read-write
    STATUS current
    DESCRIPTION "<Definition> The object is used to further define a function type when ascIOinputMapFuncType is not zero. The value of this object will identify a custom function type unique to the manufacturer specified by ascIOinputMapDevicePNN.

This allows a manufacturer to have multiple sets of functions for their one Private Node Number.
    <Object Identifier> 1.3.6.1.4.1.1206.4.2.1.13.4.1.9
    <Object Type> P"
    ::= { ascIOinputMapTableEntry 9 }

--5.13.4.10 I/O Input Map Function
ascIOinputMapFunction OBJECT-TYPE
    SYNTAX Integer32 (0..255)
    MAX-ACCESS read-write
    STATUS current
    DESCRIPTION "<Definition> This object specifies the function that is mapped to the I/O pin specified by this row.
      For example, if ascIOinputMapFuncType is zero (standard) then the function could be any AscIOinputType value such as vehicleDetector (51).
    <Object Identifier> 1.3.6.1.4.1.1206.4.2.1.13.4.1.10
    <Object Type> P"
    ::= { ascIOinputMapTableEntry 10 }

--5.13.4.11 I/O Input Map Function Index
ascIOinputMapFuncIndex OBJECT-TYPE
    SYNTAX Integer32 (0..255)
    MAX-ACCESS read-write
    STATUS current
    DESCRIPTION "<Definition> An index for the function at this table row. For example, if ascIOinputMapFuncType is zero (standard) and the ascIOinputMapFunction is vehicleDetector (51) then this index will determine which detector input it is (1 to maxVehicleDetectors).
    <Object Identifier> 1.3.6.1.4.1.1206.4.2.1.13.4.1.11
    <Object Type> P"
    ::= { ascIOinputMapTableEntry 11 }

--5.13.5    I/O Input Map Status Table
ascIOinputMapStatusTable OBJECT-TYPE
    SYNTAX SEQUENCE OF AscIOinputMapStatusTableEntry
    MAX-ACCESS not-accessible
    STATUS current
    DESCRIPTION "<Definition> A table containing status for the current mapping for an ASC controller's inputs.
    <TableType> static
    <Object Identifier> 1.3.6.1.4.1.1206.4.2.1.13.5"
    ::= { ascIOmapping 5 }

ascIOinputMapStatusTableEntry OBJECT-TYPE
    SYNTAX AscIOinputMapStatusTableEntry
    MAX-ACCESS not-accessible
    STATUS current
    DESCRIPTION "<Definition> This object defines a conceptual row in the ascIOinputMapStatusTable.
    <Object Identifier> 1.3.6.1.4.1.1206.4.2.1.13.5.1"
    INDEX { ascIOmapNumber, ascIOinputMapIOindex }
    ::= { ascIOinputMapStatusTable   1 }

AscIOinputMapStatusTableEntry ::= SEQUENCE {
   ascIOinputMapDevPinDescr   SnmpAdminString, -- description of input pin
   ascIOinputMapDevPinStatus  Integer32 }     -- 0 or 1 for active

--5.13.5.1  I/O Input Map Device Pin Description
ascIOinputMapDevPinDescr OBJECT-TYPE
    SYNTAX SnmpAdminString
    MAX-ACCESS read-only
    STATUS current
    DESCRIPTION "<Definition> This object returns the name of the input pin, such as 'C1-39 Detector 2'.
      Since the physical pins are determined by the controller hardware, the value is read-only.
    <Object Identifier> 1.3.6.1.4.1.1206.4.2.1.13.5.1.1
    <Object Type> S"
    ::= { ascIOinputMapStatusTableEntry 1 }

--5.13.5.2  I/O Input Map Device Pin Status
ascIOinputMapDevPinStatus OBJECT-TYPE
    SYNTAX Integer32 (0..1)
    MAX-ACCESS read-only
    STATUS current
    DESCRIPTION "<Definition> This object returns the current status of an input pin: inactive/OFF (0) or active/ON (1).
    <Object Identifier> 1.3.6.1.4.1.1206.4.2.1.13.5.1.2
    <Object Type> S"
    ::= { ascIOinputMapStatusTableEntry 2 }

--5.13.6    I/O Output Map Table
ascIOoutputMapTable OBJECT-TYPE
    SYNTAX SEQUENCE OF AscIOoutputMapTableEntry
    MAX-ACCESS not-accessible
    STATUS current
    DESCRIPTION "<Definition> A table containing mapping for an ASC Controller's inputs and outputs to functions.
      The number of I/O map tables is equal to the value of ascIOmaxMaps.
      The total number of rows in the table is ascIOmapMaxOutputs.
      Only one I/O map may be active at any one time, and is selected by ascIOactiveMap.
    <TableType> static
    <Object Identifier> 1.3.6.1.4.1.1206.4.2.1.13.6"
    ::= { ascIOmapping 6 }

ascIOoutputMapTableEntry OBJECT-TYPE
    SYNTAX AscIOoutputMapTableEntry
    MAX-ACCESS not-accessible
    STATUS current
    DESCRIPTION "<Definition> This object defines a conceptual row in the ascIOoutputMapTable.
    <Object Identifier> 1.3.6.1.4.1.1206.4.2.1.13.6.1"
    INDEX { ascIOmapNumber, ascIOoutputMapIOindex }
    ::= { ascIOoutputMapTable 1 }

AscIOoutputMapTableEntry ::= SEQUENCE {
   ascIOoutputMapIOindex       Integer32,   -- up to ascIOmapMaxOutputs
   ascIOoutputMapDeviceType    INTEGER,   -- enum custom, FIO,TS1,BIU,SIU,AUX, reserved
   ascIOoutputMapDevicePNN     Integer32,   -- NEMA PNN if DeviceType is custom
   ascIOoutputMapDevicePtype   Integer32,   -- Custom device type
   ascIOoutputMapDeviceAddr    Integer32,   -- only used if needed (BIU, SIU)
   ascIOoutputMapDevicePin     Integer32,   -- device I/O pin index
   ascIOoutputMapFuncType      Integer32,   -- 0=STD, else nemaPrivate vendor code
   ascIOoutputMapFuncPtype     Integer32,   -- Custom function type
   ascIOoutputMapFunction      Integer32,   -- function 
   ascIOoutputMapFuncIndex     Integer32 }  -- index if function support more than one input or output

--5.13.6.1  I/O Output Map Index
ascIOoutputMapIOindex OBJECT-TYPE
    SYNTAX Integer32 (1..65535)
    MAX-ACCESS not-accessible
    STATUS current
    DESCRIPTION "<Definition> The I/O index for this row of the table. The range is 1 to ascIOmapMaxOutputs.
    <Object Identifier> 1.3.6.1.4.1.1206.4.2.1.13.6.1.1
    <Object Type> S"
    ::= { ascIOoutputMapTableEntry 1 }

--5.13.6.2  I/O Output Map Device Type
ascIOoutputMapDeviceType OBJECT-TYPE
    SYNTAX INTEGER { unused (1),
                  custom (2),
                  fio (3),
                  ts1 (4),
                  biu (5),
                  siu (6),
                  aux (7) }
    MAX-ACCESS read-write
    STATUS current
    DESCRIPTION "<Definition> This object is an selects the device type for         this row of the table.
      A value of unused (1) means that this row of the table is unused (all values of ascIOoutputMapIOindex up to or ascIOmapMaxOutputs may not be needed by every mapping).
      A custom type is a manufacturer defined device which also requires a ascIOoutputMapDevicePNN and a ascIOoutputMapDevicePtype to fully specify the device.
      Values > 7 are reserved for future device types.
    <Object Identifier> 1.3.6.1.4.1.1206.4.2.1.13.6.1.2
    <Object Type> P"
    ::= { ascIOoutputMapTableEntry 2 }

--5.13.6.3  I/O Output Map Custom Device Manufacturer
ascIOoutputMapDevicePNN OBJECT-TYPE
    SYNTAX Integer32 (0..65535)
    MAX-ACCESS read-write
    STATUS current
    DESCRIPTION "<Definition> The object is used to further define a device type when ascIOoutputMapDeviceType is custom (2). The value of this object will be the manufacturer's Private Node Number (PNN) as assigned by NEMA (1.3.6.1.4.1.1206.3.PNN). This is the same identifier used for ASC custom blocks.
    <Object Identifier> 1.3.6.1.4.1.1206.4.2.1.13.6.1.3
    <Object Type> P"
    ::= { ascIOoutputMapTableEntry 3 }

--5.13.6.4  I/O Output Map Custom Device Type
ascIOoutputMapDevicePtype OBJECT-TYPE
    SYNTAX Integer32 (0..255)
    MAX-ACCESS read-write
    STATUS current
    DESCRIPTION "<Definition> The object is used to further define a device type when ascIOoutputMapDeviceType is custom (2). The value of this object will identify a custom device type unique to the manufacturer specified by ascIOoutputMapDevicePNN.
    <Object Identifier> 1.3.6.1.4.1.1206.4.2.1.13.6.1.4
    <Object Type> P"
    ::= { ascIOoutputMapTableEntry 4 }

--5.13.6.5  I/O Output Map Device Address
ascIOoutputMapDeviceAddr OBJECT-TYPE
    SYNTAX Integer32 (0..255)
    MAX-ACCESS read-write
    STATUS current
    DESCRIPTION "<Definition> An address for the device at this table row. The address is used for devices like BIUs and SIUs that require an address. The value should be zero if the address is not needed for this row.
      If the ascIOoutputMapDeviceType is biu (4), the address values are:
                1   - Traffic Facilities BIU #1
                2   - Traffic Facilities BIU #2
                3   - Traffic Facilities BIU #3
                4   - Traffic Facilities BIU #4
                5-8 - reserved
                9   - Detector BIU #1
                10  - Detector BIU #2
                11  - Detector BIU #3
                12  - Detector BIU #4
                13-16 - reserved
      Note that these values are the BIU SDLC address + 1.

      If the ascIOoutputMapDeviceType is siu (5), the address values  are:
                1  - reserved
                2  - 14-pack output SIU position 1
                3  - reserved
                4  - 14-pack output SIU position 3
                5  -  6-pack output SIU position 4
                6  -  6-pack output SIU position 1
                7  -  6-pack output SIU position 2
                8  -  6-pack output SIU position 3
                9  - reserved
                10 - input SIU #1
                11 - input SIU #2
                12 - input SIU #3
                13 - input SIU #4
                14 - input SIU #5
                15 - reserved
      Note that these values are the SIU SDLC address + 1.
    <Object Identifier> 1.3.6.1.4.1.1206.4.2.1.13.6.1.5
    <Object Type> P"
    ::= { ascIOoutputMapTableEntry 5 }

--5.13.6.6  I/O Output Map Device Pin
ascIOoutputMapDevicePin OBJECT-TYPE
    SYNTAX Integer32 (0..255)
    MAX-ACCESS read-write
    STATUS current
    DESCRIPTION "<Definition> An index for the I/O pin at this table row. The range for this value will depend upon the value of other objects in the row.
      The range for ascIOmapDeviceType:
            fio (3) pin range is AscIOmapFIOoutputs
            ts1 (4) pin range is AscIOmapTS1outputs
            biu (5) pin range is AscIOmapBIUoutputs
            siu (6) pin range is AscIOmapSIUoutputs
            aux (7) pin range is AscIOmapAUXoutputs
      The range for a custom device type will be determined by the manufacturer defining it.
    <Object Identifier> 1.3.6.1.4.1.1206.4.2.1.13.6.1.6
    <Object Type> P"
    ::= { ascIOoutputMapTableEntry 6 }

--5.13.6.7  I/O Output Map Function Type
ascIOoutputMapFuncType OBJECT-TYPE
    SYNTAX Integer32 (0..65535)
    MAX-ACCESS read-write
    STATUS current
    DESCRIPTION "<Definition> This object selects the function type for this row of the table. A value of zero references the standard output functions defined by AscIOoutputType and the ascIOoutputMapFunction.
      Any other value is a manufacturer's Private Node Number (PNN) as assigned by NEMA (1.3.6.1.4.1.1206.3.PNN). In this case the function is defined by the PNN (the manufacturer), ascIOoutputMapFuncPtype (which of the manufacturer's multiple function sets), and the ascIOoutputMapFunction.
    <Object Identifier> 1.3.6.1.4.1.1206.4.2.1.13.6.1.7
    <Object Type> P"
    ::= { ascIOoutputMapTableEntry 7 }

--5.13.6.8  I/O Output Map Custom Function Type
ascIOoutputMapFuncPtype OBJECT-TYPE
    SYNTAX Integer32 (0..255)
    MAX-ACCESS read-write
    STATUS current
    DESCRIPTION "<Definition> The object is used to further define a function type when ascIOoutputMapFuncType is not zero. The value of this object will identify a custom function type unique to the manufacturer specified by ascIOoutputMapDevicePNN.
    <Object Identifier> 1.3.6.1.4.1.1206.4.2.1.13.6.1.8
    <Object Type> P"
    ::= { ascIOoutputMapTableEntry 8 }

--5.13.6.9  I/O Output Map Function
ascIOoutputMapFunction OBJECT-TYPE
    SYNTAX Integer32 (0..255)
    MAX-ACCESS read-write
    STATUS current
    DESCRIPTION "<Definition> This object specifies the function that is mapped to the I/O pin specified by this row. For example, if ascIOoutputMapFuncType is zero (standard) then the function could be any AscIOoutputType value such as channelGreen (6).
    <Object Identifier> 1.3.6.1.4.1.1206.4.2.1.13.6.1.9
    <Object Type> P"
    ::= { ascIOoutputMapTableEntry 9 }

--5.13.6.10 I/O Output Map Function Index
ascIOoutputMapFuncIndex OBJECT-TYPE
    SYNTAX Integer32 (0..255)
    MAX-ACCESS read-write
    STATUS current
    DESCRIPTION "<Definition> An index for the function at this table row. For example, if ascIOoutputMapFuncType is zero (standard) and the ascIOoutputMapFunction is channelGreen (6), then this index will determine which channelGreen output it is (1 to maxChannels).
    <Object Identifier> 1.3.6.1.4.1.1206.4.2.1.13.6.1.11
    <Object Type> P"
    ::= { ascIOoutputMapTableEntry 11 }

--5.13.7    I/O Output Map Status Table
ascIOoutputMapStatusTable OBJECT-TYPE
    SYNTAX SEQUENCE OF AscIOoutputMapStatusTableEntry
    MAX-ACCESS not-accessible
    STATUS current
    DESCRIPTION "<Definition> A table containing status for the current mapping for an ASC controller's outputs.
    <TableType> static
    <Object Identifier> 1.3.6.1.4.1.1206.4.2.1.13.7"
    ::= { ascIOmapping 7 }

ascIOoutputMapStatusTableEntry OBJECT-TYPE
    SYNTAX AscIOoutputMapStatusTableEntry
    MAX-ACCESS not-accessible
    STATUS current
    DESCRIPTION "<Definition> This object defines a conceptual row in the ascIOoutputMapStatusTable.
    <Object Identifier> 1.3.6.1.4.1.1206.4.2.1.13.7.1"
    INDEX { ascIOmapNumber, ascIOoutputMapIOindex }
    ::= { ascIOoutputMapStatusTable   1 }

AscIOoutputMapStatusTableEntry ::= SEQUENCE {
   ascIOoutputMapDevPinDescr   SnmpAdminString, -- description of output pin
   ascIOoutputMapDevPinStatus  Integer32 }     -- 0 or 1 for active

--5.13.7.1  I/O Output Map Device Pin Description
ascIOoutputMapDevPinDescr OBJECT-TYPE
    SYNTAX SnmpAdminString
    MAX-ACCESS read-only
    STATUS current
    DESCRIPTION "<Definition> This object returns the name of the output pin, such as 'C1-39 Detector 2'. Since the physical pins are determined by the controller hardware, the value is read-only.
    <Object Identifier> 1.3.6.1.4.1.1206.4.2.1.13.7.1.1
    <Object Type> S"
    ::= { ascIOoutputMapStatusTableEntry 1 }

--5.13.7.2  I/O Output Map Device Pin Status
ascIOoutputMapDevPinStatus OBJECT-TYPE
    SYNTAX Integer32 (0..1)
    MAX-ACCESS read-only
    STATUS current
    DESCRIPTION "<Definition> This object returns the current status of an output pin: inactive/OFF (0) or active/ON (1).
    <Object Identifier> 1.3.6.1.4.1.1206.4.2.1.13.7.1.2"
    ::= { ascIOoutputMapStatusTableEntry 2 }

--5.13.8    I/O Map Description Table
ascIOmapDescriptionTable OBJECT-TYPE
    SYNTAX SEQUENCE OF AscIOmapDescriptionTableEntry
    MAX-ACCESS not-accessible
    STATUS current
    DESCRIPTION "<Definition> A table containing mapping for an ASC Controller's inputs and outputs to functions. The number of I/O map tables is equal to the value of ascIOmaxMaps.
      Each table contains a row for each input the supported by the ASC. The total number of rows in the table is ascIOmapMaxInputs.
      Only one I/O input map may be active at any one time, and is selected by ascIOactiveMap.
    <TableType> static
    <Object Identifier> 1.3.6.1.4.1.1206.4.2.1.13.8"
    ::= { ascIOmapping 8 }

ascIOmapDescriptionTableEntry OBJECT-TYPE
    SYNTAX AscIOmapDescriptionTableEntry
    MAX-ACCESS not-accessible
    STATUS current
    DESCRIPTION "<Definition> This object defines a conceptual set of rows in the ascIOinputMapTable and ascIOoutputMapTable tables corresponding to an ascIOmapNumber.
    <Object Identifier> 1.3.6.1.4.1.1206.4.2.1.13.8.1"
    INDEX { ascIOmapNumber }
    ::= { ascIOmapDescriptionTable   1 }

AscIOmapDescriptionTableEntry ::= SEQUENCE {
   ascIOmapDescription   SnmpAdminString }

--5.13.8.1  I/O Map Description
ascIOmapDescription OBJECT-TYPE
    SYNTAX SnmpAdminString
    MAX-ACCESS read-write
    STATUS current
    DESCRIPTION "<Definition> This object returns the name of the I/O map.  There is only one name for the I/O map for each value of ascIOmapNumber.
      This map name corresponds to ascIOinputMapTable and ascIOoutputMapTable rows with the same ascIOmapNumber index.
    <Object Identifier> 1.3.6.1.4.1.1206.4.2.1.13.8.1.1
    <Object Type> P"
    ::= { ascIOmapDescriptionTableEntry 1 }


--5.13.9    I/O Map Input Functions
ascIOmapInputFunctions OBJECT IDENTIFIER ::= { ascIOmapping 9 }

-- Enumeration for I/O mapping input functions
AscIOinputType ::= INTEGER {
    unusedInput             (1),    -- an input pin that is unused, not mapped
    ioUsedAsOutput          (2),    -- an I/O pin that is being used as an output (SIU or BIU)
    logicInput              (3),    -- an input that is used only by the programmable logic
    addressBit              (4), 
    alarmInput              (5),
    alternateSequence       (6),
    autoFlashRequest        (7),
    cabinetDoorOpen         (8),
    callToNonActuated       (9),
    clockUpdate             (10),
    conflictMonitorStatus   (11),
    cycleAdvance            (12),
    dimmingEnable           (13),
    externalStart           (14),
    forceOffRing            (15),
    freeRequest             (16),
    hardwareControl         (17),
    indicatorLampControl    (18),
    inhibitMaxRing          (19),
    intervalAdvance         (20),
    localFlashSense         (21),
    manualControlEnable     (22),
    max2Ring                (23),
    max3AllRings            (24),
    max4AllRings            (25),
    maxRecall               (26),
    maxWalk                 (27),
    minRecall               (28),
    mmuCmuFlashSense        (29),
    modeSelectBit           (30),
    offsetInput             (31),
    omitRedClearRing        (32),
    patternSelect           (33),
    pedestrianDetector      (34),
    pedestrianOmit          (35),
    pedestrianRecycleRing   (36),
    phaseHold               (37),
    phaseOmit               (38),
    preemptGateDown         (39),
    preemptGateUp           (40),
    preemptHealthy          (41),
    preemptInput            (42),
    preemptInputAdvanced    (43),
    priorityCheckout        (44),
    priorityRequest         (45),
    redRestRing             (46),
    specialFunctionInput    (47),
    stopTimeAllRings        (48),
    stopTimeRing            (49),
    tbcOnline               (50),
    testInput               (51),
    timingPlanInput         (52),
    vehicleDetector         (53),
    vehicleDetectorFault    (54),
    walkRestModifier        (55) }

--5.13.9.1  I/O Map Maximum Input Functions
ascIOmapMaxInputFunctions OBJECT-TYPE
    SYNTAX Integer32 (1..255)
    MAX-ACCESS read-only
    STATUS current
    DESCRIPTION "<Definition> This object contains the maximum number of I/O mapping input functions this ASC supports. This object indicates the number of rows in the ascIOmapInputFuncTable.
      The value of this object is equal to the number of AscIOinputType enumerations.
    <Object Identifier> 1.3.6.1.4.1.1206.4.2.1.13.9.1
    <Object Type> S"
    ::= { ascIOmapInputFunctions 1 }

--5.13.9.2  I/O Map Input Functions Table
ascIOmapInputFuncTable OBJECT-TYPE
    SYNTAX SEQUENCE OF AscIOmapInputFuncEntry
    MAX-ACCESS not-accessible
    STATUS current
    DESCRIPTION "<Definition> A table referencing the ASC I/O mapping input functions. These are functions that may be assigned to the ASC inputs.
      The number of rows in this table is equal to ascIOmapMaxInputFunctions. The entries in this table correspond to the values of the AscIOinputType enumeration.
    <TableType> static
    <Object Identifier> 1.3.6.1.4.1.1206.4.2.1.13.9.2"
    ::= { ascIOmapInputFunctions 2 }

ascIOmapInputFuncEntry OBJECT-TYPE
    SYNTAX AscIOmapInputFuncEntry
    MAX-ACCESS not-accessible
    STATUS current
    DESCRIPTION "<Definition> This object defines a conceptual row in the ascIOmapInputFuncTable.
    <Object Identifier> 1.3.6.1.4.1.1206.4.2.1.13.9.2.1"
    INDEX { ascIOinputIndex }
    ::= { ascIOmapInputFuncTable 1 }

AscIOmapInputFuncEntry ::= SEQUENCE {
    ascIOinputIndex          Integer32,
    ascIOinputMaxFuncIndex   Integer32,
    ascIOinputFunctionName   SnmpAdminString }

--5.13.9.2.1    I/O Map Input Functions Table Index
ascIOinputIndex OBJECT-TYPE
    SYNTAX Integer32 (1..255)
    MAX-ACCESS not-accessible
    STATUS current
    DESCRIPTION "<Definition> Indicates the row number of the entry in the ascIOmapInputFuncTable. The value of this object shall not exceed the ascIOmapMaxInputFunctions value.
      These indexes correspond to the values of the AscIOinputType enumeration.
    <Object Identifier> 1.3.6.1.4.1.1206.4.2.1.13.9.2.1.1
    <Object Type> S"
    ::= { ascIOmapInputFuncEntry 1 }

--5.13.9.2.2    I/O Map Input Function Maximum Index
ascIOinputMaxFuncIndex OBJECT-TYPE
    SYNTAX Integer32 (1..255)
    MAX-ACCESS read-only
    STATUS current
    DESCRIPTION "<Definition> Some input functions support an array of inputs. This object indicates the maximum array index for this input function.
    <Object Identifier> 1.3.6.1.4.1.1206.4.2.1.13.9.2.1.2
    <Object Type> S"
    ::= { ascIOmapInputFuncEntry 2 }

--5.13.9.2.3    I/O Map Input Function Name
ascIOinputFunctionName OBJECT-TYPE
    SYNTAX SnmpAdminString
    MAX-ACCESS read-only
    STATUS current
    DESCRIPTION "<Definition> This object contains an ASCII string describing the input function.
    <Object Identifier> 1.3.6.1.4.1.1206.4.2.1.13.9.2.1.3
    <Object Type> S"
    ::= { ascIOmapInputFuncEntry 3 }

--5.13.10   I/O Map Output Functions
ascIOmapOutputFunctions OBJECT IDENTIFIER
    ::= { ascIOmapping 10 }

-- Enumeration for I/O mapping output functions
AscIOoutputType ::= INTEGER {
    unusedOutput            (1),    -- an output pin that is unused, not mapped
    ioUsedAsInput           (2),    -- an I/O pin that is being used as an input (SIU or BIU)
    logicOutput             (3),    -- an output function from the programmable logic
    advWarnGrn              (4), 
    advWarnRed              (5),
    alarmOutput             (6),
    automaticFlashStatus    (7),
    channelGreen            (8),
    channelRed              (9),
    channelYellow           (10),
    codedStatusBitA         (11),
    codedStatusBitB         (12),
    codedStatusBitC         (13),
    detectorResetSlots      (14),
    detectorReset           (15),
    faultMonitor            (16),
    flashingLogic           (17),
    freeStatus              (18),
    offsetOutput            (19),
    phaseCheck              (20),
    phaseNext               (21),
    phaseOn                 (22),
    preemptActive           (23),
    preemptActiveAdvanced   (24),
    specialFunctionOutput   (25),
    tbcAuxOutput            (26),
    timingPlanOutput        (27),
    voltageMonitor          (28),
    watchdog                (29) }

--5.13.10.1 I/O Map Maximum Output Functions
ascIOmapMaxOutputFunctions OBJECT-TYPE
    SYNTAX Integer32 (1..255)
    MAX-ACCESS read-only
    STATUS current
    DESCRIPTION "<Definition> This object contains the maximum number of I/O mapping output functions this ASC supports. This object indicates the number of rows in the ascIOmapOutputFuncTable.
      The value of this object is equal to the number of AscIOoutputType enumerations.
    <Object Identifier> 1.3.6.1.4.1.1206.4.2.1.13.10.1
    <Object Type> S"
    ::= { ascIOmapOutputFunctions 1 }

--5.13.10.2 I/O Map Output Functions Table
ascIOmapOutputFuncTable OBJECT-TYPE
 SYNTAX SEQUENCE OF AscIOmapOutputFuncEntry
 MAX-ACCESS not-accessible
 STATUS current
 DESCRIPTION "<Definition> A table referencing the ASC I/O mapping output functions. These are functions that may be assigned         to the ASC outputs.
      The number of rows in this table is equal to ascIOmapMaxOutputFunctions.
      The entries in this table correspond to the values of the AscIOoutputType enumeration.
    <TableType> static
    <Object Identifier> 1.3.6.1.4.1.1206.4.2.1.13.10.2"
    ::= { ascIOmapOutputFunctions 2 }

ascIOmapOutputFuncEntry OBJECT-TYPE
    SYNTAX AscIOmapOutputFuncEntry
    MAX-ACCESS not-accessible
    STATUS current
    DESCRIPTION "<Definition> This object defines a conceptual row in the ascIOmapOutputFuncTable.
    <Object Identifier> 1.3.6.1.4.1.1206.4.2.1.13.10.2.1"
    INDEX { ascIOoutputIndex }
    ::= { ascIOmapOutputFuncTable 1 }

AscIOmapOutputFuncEntry ::= SEQUENCE {
    ascIOoutputIndex          Integer32,
    ascIOoutputMaxFuncIndex   Integer32,
    ascIOoutputFunctionName   SnmpAdminString }

--5.13.10.2.1   I/O Map Output Functions Table Index
ascIOoutputIndex OBJECT-TYPE
    SYNTAX Integer32 (1..255)
    MAX-ACCESS not-accessible
    STATUS current
    DESCRIPTION "<Definition> Indicates the row number of the entry in the ascIOmapOutputFuncTable. The value of this object shall not exceed the ascIOmapMaxOutputFunctions value. These indexes correspond to the values of the AscIOoutputType enumeration.
    <Object Identifier> 1.3.6.1.4.1.1206.4.2.1.13.10.2.1.1
    <Object Type> S"
    ::= { ascIOmapOutputFuncEntry 1 }

--5.13.10.2.2   I/O Map Output Function Maximum Index
ascIOoutputMaxFuncIndex OBJECT-TYPE
    SYNTAX Integer32 (1..255)
    MAX-ACCESS read-only
    STATUS current
    DESCRIPTION "<Definition> Some output functions support an array of outputs. This object indicates the maximum array index for this output function.
    <Object Identifier> 1.3.6.1.4.1.1206.4.2.1.13.10.2.1.2
    <Object Type> S"
    ::= { ascIOmapOutputFuncEntry 2 }

--5.13.10.2.3   I/O Map Output Function Name
ascIOoutputFunctionName OBJECT-TYPE
    SYNTAX SnmpAdminString
    MAX-ACCESS read-only
    STATUS current
    DESCRIPTION "<Definition> This object contains an ASCII string describing the output function.
    <Object Identifier> 1.3.6.1.4.1.1206.4.2.1.13.10.2.1.3
    <Object Type> S"
    ::= { ascIOmapOutputFuncEntry 3 }

--5.13.11   I/O Map FIO Pins
ascIOmapFIO OBJECT IDENTIFIER ::= { ascIOmapping 11 }

--5.13.11.1 I/O Map FIO Input Pins
AscIOmapFIOinputs ::= INTEGER { -- Enumeration for 2070-2A FIO (170) inputs
    pinC1-39 (1),   -- Detector 2
    pinC1-40 (2),   -- Detector 16
    pinC1-41 (3),   -- Detector 8
    pinC1-42 (4),   -- Detector 22
    pinC1-43 (5),   -- Detector 3
    pinC1-44 (6),   -- Detector 17
    pinC1-45 (7),   -- Detector 9
    pinC1-46 (8),   -- Detector 23
    pinC1-47 (9),   -- Detector 6
    pinC1-48 (10),  -- Detector 20
    pinC1-49 (11),  -- Detector 12
    pinC1-50 (12),  -- Detector 26
    pinC1-51 (13),  -- RR1 Preempt
    pinC1-52 (14),  -- RR2 Preempt
    pinC1-53 (15),  -- Manual Control
    pinC1-54 (16),  -- Spare
    pinC1-55 (17),  -- Detector 15
    pinC1-56 (18),  -- Detector 1
    pinC1-57 (19),  -- Detector 21
    pinC1-58 (20),  -- Detector 7
    pinC1-59 (21),  -- Detector 27
    pinC1-60 (22),  -- Detector 13
    pinC1-61 (23),  -- Detector 28
    pinC1-62 (24),  -- Detector 14
    pinC1-63 (25),  -- Detector 4
    pinC1-64 (26),  -- Detector 18
    pinC1-65 (27),  -- Detector 10
    pinC1-66 (28),  -- Detector 24
    pinC1-67 (29),  -- Ped Detector 1
    pinC1-68 (30),  -- Ped Detector 3
    pinC1-69 (31),  -- Ped Detector 2
    pinC1-70 (32),  -- Ped Detector 4
    pinC1-71 (33),  -- EVA Preempt
    pinC1-72 (34),  -- EVB Preempt
    pinC1-73 (35),  -- EVC Preempt
    pinC1-74 (36),  -- EVD Preempt
    pinC1-75 (37),  -- Spare
    pinC1-76 (38),  -- Detector 5
    pinC1-77 (39),  -- Detector 19
    pinC1-78 (40),  -- Detector 11
    pinC1-79 (41),  -- Detector 25
    pinC1-80 (42),  -- Interval Advance
    pinC1-81 (43),  -- Flash Sense
    pinC1-82 (44),  -- Stop Time
    pinC11-10 (45), -- C11 inputs all spare
    pinC11-11 (46),
    pinC11-12 (47),
    pinC11-13 (48),
    pinC11-15 (49),
    pinC11-16 (50),
    pinC11-17 (51),
    pinC11-18 (52),
    pinC11-19 (53),
    pinC11-20 (54),
    pinC11-21 (55),
    pinC11-22 (56),
    pinC11-23 (57),
    pinC11-24 (58),
    pinC11-25 (59),
    pinC11-26 (60),
    pinC11-27 (61),
    pinC11-28 (62),
    pinC11-29 (63),
    pinC11-30 (64) }

--5.13.11.2 I/O Map FIO Output Pins
AscIOmapFIOoutputs ::= INTEGER {    -- Enumeration for 2070-2A FIO (170) outputs
    pinC1-2   (1),   -- Ped 4 red
    pinC1-3   (2),   -- Ped 4 green
    pinC1-4   (3),   -- Phase 4 red
    pinC1-5   (4),   -- Phase 4 yellow
    pinC1-6   (5),   -- Phase 4 green
    pinC1-7   (6),   -- Phase 3 red
    pinC1-8   (7),   -- Phase 3 yellow
    pinC1-9   (8),   -- Phase 3 green
    pinC1-10  (9),   -- Ped 2 red
    pinC1-11  (10),  -- Ped 2 green
    pinC1-12  (11),  -- Phase 2 red
    pinC1-13  (12),  -- Phase 2 yellow
    pinC1-15  (13),  -- Phase 2 green
    pinC1-16  (14),  -- Phase 1 red
    pinC1-17  (15),  -- Phase 1 yellow
    pinC1-18  (16),  -- Phase 1 green
    pinC1-19  (17),  -- Ped 8 red
    pinC1-20  (18),  -- Ped 8 green
    pinC1-21  (19),  -- Phase 8 red
    pinC1-22  (20),  -- Phase 8 yellow
    pinC1-23  (21),  -- Phase 8 green
    pinC1-24  (22),  -- Phase 7 red
    pinC1-25  (23),  -- Phase 7 yellow
    pinC1-26  (24),  -- Phase 7 green
    pinC1-27  (25),  -- Ped 6 red
    pinC1-28  (26),  -- Ped 6 green
    pinC1-29  (27),  -- Phase 6 red
    pinC1-30  (28),  -- Phase 6 yellow
    pinC1-31  (29),  -- Phase 6 green
    pinC1-32  (30),  -- Phase 5 red
    pinC1-33  (31),  -- Phase 5 yellow
    pinC1-34  (32),  -- Phase 5 green
    pinC1-35  (33),  -- Ped 2 yellow
    pinC1-36  (34),  -- Ped 6 yellow
    pinC1-37  (35),  -- Ped 4 yellow
    pinC1-38  (36),  -- Ped 8 yellow
    pinC1-83  (37),  -- Spare     
    pinC1-84  (38),  -- Spare     
    pinC1-85  (39),  -- Overlap D red
    pinC1-86  (40),  -- Overlap D yellow
    pinC1-87  (41),  -- Overlap D green
    pinC1-88  (42),  -- Overlap C red
    pinC1-89  (43),  -- Overlap C yellow
    pinC1-90  (44),  -- Overlap C green
    pinC1-91  (45),  -- Spare     
    pinC1-93  (46),  -- Spare     
    pinC1-94  (47),  -- Overlap B red
    pinC1-95  (48),  -- Overlap B yellow
    pinC1-96  (49),  -- Overlap B green
    pinC1-97  (50),  -- Overlap A red
    pinC1-98  (51),  -- Overlap A yellow
    pinC1-99  (52),  -- Overlap A green
    pinC1-100 (53),  -- Spare    
    pinC1-101 (54),  -- Flash status
    pinC1-102 (55),  -- Detector reset
    pinC1-103 (56),  -- Watchdog
    pinC11-1  (57),  -- all C11 outputs are spare
    pinC11-2  (58),
    pinC11-3  (59),
    pinC11-4  (60),
    pinC11-5  (61),
    pinC11-6  (62),
    pinC11-7  (63),
    pinC11-8  (64) }

--5.13.12   I/O Map TS1 Pins
ascIOmapTS1 OBJECT IDENTIFIER ::= { ascIOmapping 12 }

--5.13.12.1 I/O Map TS1 Input Pins
AscIOmapTS1inputs ::= INTEGER { -- Enumeration for type 2070-8 NEMA TS1 inputs
    pinA-f  (1),   -- Vehicle Detector 1  
    pinA-g  (2),   -- Ped Detector 1  
    pinA-h  (3),   -- Hold 1     
    pinA-i  (4),   -- Force Off Ring 1
    pinA-j  (5),   -- Min Recall 
    pinA-k  (6),   -- Manual Control
    pinA-m  (7),   -- CNA 1      
    pinA-n  (8),   -- Test A     
    pinA-q  (9),   -- Mode Bit A 
    pinA-v  (10),  -- Ped Omit 2 
    pinA-w  (11),  -- Omit Red Ring 1
    pinA-x  (12),  -- Red Rest Ring 1
    pinA-y  (13),  -- Mode Bit B 
    pinA-z  (14),  -- CNA 2      
    pinA-K  (15),  -- Vehicle Detector 2  
    pinA-L  (16),  -- Ped Detector 2  
    pinA-M  (17),  -- Hold 2     
    pinA-N  (18),  -- Stop Time Ring 1
    pinA-P  (19),  -- Inhibit Max Ring 1 
    pinA-R  (20),  -- External Start
    pinA-S  (21),  -- Interval Advance
    pinA-T  (22),  -- Lamp Control
    pinA-AA (23),  -- Test B     
    pinA-BB (24),  -- Walk Rest Modifier
    pinA-EE (25),  -- Ped Omit 1 
    pinA-FF (26),  -- Ped Recycle Ring 1
    pinA-GG (27),  -- Max 2 Ring 1   
    pinA-HH (28),  -- Mode Bit C 
    pinB-g  (29),  -- Phase Omit 4 
    pinB-h  (30),  -- Hold 4     
    pinB-i  (31),  -- Hold 3     
    pinB-j  (32),  -- Ped Omit 3 
    pinB-k  (33),  -- Ped Omit 6 
    pinB-m  (34),  -- Ped Omit 7 
    pinB-n  (35),  -- Ped Omit 8 
    pinB-v  (36),  -- Spare      
    pinB-x  (37),  -- Ped Omit 4 
    pinB-z  (38),  -- Max 2 Ring 2   
    pinB-B  (39),  -- Spare      
    pinB-L  (40),  -- Vehicle Detector 4  
    pinB-M  (41),  -- Ped Detector 4  
    pinB-N  (42),  -- Vehicle Detector 3  
    pinB-P  (43),  -- Ped Detector 3  
    pinB-R  (44),  -- Phase Omit 3 
    pinB-S  (45),  -- Phase Omit 2 
    pinB-T  (46),  -- Ped Omit 5 
    pinB-U  (47),  -- Phase Omit 1 
    pinB-V  (48),  -- Ped RECY R2
    pinB-W  (49),  -- Spare      
    pinB-X  (50),  -- Spare      
    pinC-a  (51),  -- Inhibit Max Ring 2 
    pinC-b  (52),  -- Ttest C     
    pinC-m  (53),  -- Hold 5     
    pinC-n  (54),  -- Phase Omit 5 
    pinC-p  (55),  -- Hold 6     
    pinC-q  (56),  -- Phase Omit 6 
    pinC-r  (57),  -- Phase Omit 7 
    pinC-s  (58),  -- Phase Omit 8 
    pinC-t  (59),  -- Vehicle Detector 8  
    pinC-u  (60),  -- Red Rest Ring 2
    pinC-v  (61),  -- Omit Red Ring 2
    pinC-P  (62),  -- Vehicle Detector 5  
    pinC-R  (63),  -- Ped Detector 5  
    pinC-S  (64),  -- Vehicle Detector 6  
    pinC-T  (65),  -- Ped Detector 6  
    pinC-U  (66),  -- Ped Detector 7  
    pinC-V  (67),  -- Vehicle Detector 7  
    pinC-W  (68),  -- Ped Detector 8  
    pinC-X  (69),  -- Hold 8     
    pinC-Y  (70),  -- Force Off Ring 2
    pinC-Z  (71),  -- Stop Time Ring 2
    pinC-EE (72),  -- Hold 7     
    pinD-a  (73),  -- Spare      
    pinD-b  (74),  -- Alarm 1
    pinD-c  (75),  -- Alarm 2    
    pinD-d  (76),  -- Alarm 3    
    pinD-e  (77),  -- Alarm 4    
    pinD-f  (78),  -- Alarm 5    
    pinD-g  (79),  -- Flash In   
    pinD-h  (80),  -- Conflict Monitor Status
    pinD-i  (81),  -- Door Open
    pinD-j  (82),  -- Special Function 1
    pinD-k  (83),  -- Special Function 2
    pinD-m  (84),  -- Special Function 3
    pinD-n  (85),  -- Special Function 4
    pinD-p  (86),  -- Special Function 5
    pinD-q  (87),  -- Special Function 6
    pinD-r  (88),  -- Special Function 7
    pinD-s  (89),  -- Special Function 8
    pinD-t  (90),  -- Preempt 1  
    pinD-u  (91),  -- Preempt 2  
    pinD-v  (92),  -- Preempt 3  
    pinD-w  (93),  -- Preempt 4  
    pinD-x  (94),  -- Preempt 5  
    pinD-y  (95),  -- Preempt 6  
    pinD-A  (96),  -- Vehicle Detector  9 
    pinD-B  (97),  -- Vehicle Detector 10 
    pinD-C  (98),  -- Vehicle Detector 11 
    pinD-D  (99),  -- Vehicle Detector 12 
    pinD-E  (100), -- Vehicle Detector 13 
    pinD-F  (101), -- Vehicle Detector 14 
    pinD-G  (102), -- Vehicle Detector 15 
    pinD-H  (103), -- Vehicle Detector 16 
    pinD-J  (104), -- Vehicle Detector 17 
    pinD-K  (105), -- Vehicle Detector 18 
    pinD-L  (106), -- Vehicle Detector 19 
    pinD-M  (107), -- Vehicle Detector 20 
    pinD-N  (108), -- Vehicle Detector 21 
    pinD-P  (109), -- Vehicle Detector 22 
    pinD-R  (110), -- Vehicle Detector 23 
    pinD-S  (111), -- Vehicle Detector 24 
    pinD-T  (112), -- Clock Update
    pinD-U  (113), -- Hardware Control
    pinD-V  (114), -- Cycle Advance
    pinD-W  (115), -- Max 3 Select
    pinD-X  (116), -- Max 4 Select
    pinD-Y  (117), -- Free
    pinD-Z  (118), -- Spare      
    pinD-KK (119), -- Spare      
    pinD-MM (120) } -- Spare      

--5.13.12.2 I/O Map TS1 Output Pins
AscIOmapTS1outputs ::= INTEGER {    -- Enumeration for 2070-8 NEMA TS1 outputs
    pinA-a  (1),   -- Ped 1 Yellow
    pinA-b  (2),   -- Phase 2 Yellow
    pinA-c  (3),   -- Phase 2 Green
    pinA-d  (4),   -- Phase Check 2
    pinA-e  (5),   -- Phase On 2   
    pinA-r  (6),   -- Status B Ring 1
    pinA-s  (7),   -- Phase 1 Green
    pinA-t  (8),   -- Ped 1 Green
    pinA-u  (9),   -- Phase Check 1
    pinA-A  (10),  -- Fault Monitor
    pinA-C  (11),  -- Voltage Monitor
    pinA-D  (12),  -- Phase 1 Red
    pinA-E  (13),  -- Ped 1 Red
    pinA-F  (14),  -- Phase 2 Red
    pinA-G  (15),  -- Ped 2 Red
    pinA-H  (16),  -- Ped 2 Yellow
    pinA-J  (17),  -- Ped 2 Green
    pinA-X  (18),  -- Flashing Logic
    pinA-Y  (19),  -- Status C Ring 1
    pinA-Z  (20),  -- Phase 1 Yellow
    pinA-CC (21),  -- Status A Ring 1
    pinA-DD (22),  -- Phase ON 1   
    pinB-a  (23),  -- Ped 3 Red
    pinB-b  (24),  -- Phase 4 Green
    pinB-c  (25),  -- Phase 4 Yellow
    pinB-d  (26),  -- Ped 4 Green
    pinB-e  (27),  -- Phase On 4   
    pinB-f  (28),  -- Phase Next 4 
    pinB-p  (29),  -- Overlap A Yellow
    pinB-q  (30),  -- Overlap A Red
    pinB-r  (31),  -- Phase Check 3
    pinB-s  (32),  -- Phase On 3   
    pinB-t  (33),  -- Phase Next 3 
    pinB-u  (34),  -- Overlap D Red
    pinB-w  (35),  -- Overlap D Green
    pinB-A  (36),  -- Phase Next 1 
    pinB-C  (37),  -- Phase Next 2 
    pinB-D  (38),  -- Phase 3 Green
    pinB-E  (39),  -- Phase 3 Yellow
    pinB-F  (40),  -- Phase 3 Red
    pinB-G  (41),  -- Phase 4 Red
    pinB-H  (42),  -- Ped 4 Yellow
    pinB-J  (43),  -- Ped 4 Red
    pinB-K  (44),  -- Phase Check 4
    pinB-Y  (45),  -- Ped 3 Green
    pinB-Z  (46),  -- Ped 3 Yellow
    pinB-AA (47),  -- Overlap A Green
    pinB-BB (48),  -- Overlap B Yellow
    pinB-CC (49),  -- Overlap B Red
    pinB-DD (50),  -- Overlap C Red
    pinB-EE (51),  -- Overlap D Yellow
    pinB-FF (52),  -- Overlap C Green
    pinB-GG (53),  -- Overlap B Green
    pinB-HH (54),  -- Overlap C Yellow
    pinC-c  (55),  -- Status C Ring 2
    pinC-d  (56),  -- Ped 8 Green
    pinC-e  (57),  -- Phase 8 Yellow
    pinC-f  (58),  -- Phase 7 Green
    pinC-g  (59),  -- Phase 6 Green
    pinC-h  (60),  -- Phase 6 Yellow
    pinC-i  (61),  -- Phase 5 Green
    pinC-j  (62),  -- Ped 5 Green
    pinC-k  (63),  -- Phase Check 5
    pinC-w  (64),  -- Ped 8 Yellow
    pinC-x  (65),  -- Phase 8  Green
    pinC-y  (66),  -- Ped 7 Red
    pinC-z  (67),  -- Ped 6 Red
    pinC-A  (68),  -- Status A Ring 2
    pinC-B  (69),  -- Status B Ring 2
    pinC-C  (70),  -- Ped 8 Red
    pinC-D  (71),  -- Phase 8 Red
    pinC-E  (72),  -- Phase 7 Yellow
    pinC-F  (73),  -- Phase 7 Red
    pinC-G  (74),  -- Phase 6 Red
    pinC-H  (75),  -- Phase 5 Red
    pinC-J  (76),  -- Phase 5 Yellow
    pinC-K  (77),  -- Ped 5 Yellow
    pinC-L  (78),  -- Ped 5 Red
    pinC-M  (79),  -- Phase Next 5 
    pinC-N  (80),  -- Phase On 5   
    pinC-AA (81),  -- Ped 6 Yellow
    pinC-BB (82),  -- Phase Check 6
    pinC-CC (83),  -- Phase ON 6   
    pinC-DD (84),  -- Phase Next 6 
    pinC-FF (85),  -- Phase Check 8
    pinC-GG (86),  -- Phase On 8   
    pinC-HH (87),  -- Phase Next 8 
    pinC-JJ (88),  -- Ped 7 Green
    pinC-KK (89),  -- Ped 7 Yellow
    pinC-LL (90),  -- Ped 6 Green
    pinC-MM (91),  -- Phase Check 7
    pinC-NN (92),  -- Phase On 7   
    pinC-PP (93),  -- Phase Next 7 
    pinD-z  (94),  -- Alarm 1    
    pinD-AA (95),  -- Alarm 2    
    pinD-BB (96),  -- Special Function 1
    pinD-CC (97),  -- Special Function 2
    pinD-DD (98),  -- Special Function 3
    pinD-EE (99),  -- Special Function 4
    pinD-FF (100), -- Special Function 5
    pinD-GG (101), -- Special Function 6
    pinD-HH (102), -- Special Function 7
    pinD-JJ (103), -- Special Function 8
    pinD-LL (104) } -- Detector Reset

--5.13.13   I/O Map TS2 BIU Pins
ascIOmapBIU OBJECT IDENTIFIER ::= { ascIOmapping 13 }

--5.13.13.1 I/O Map TS2 BIU Input Pins
AscIOmapBIUinputs ::= INTEGER { -- Enumeration for NEMA TS2 BIU inputs (for each BIU)
    biuInputIO1   (1),
    biuInputIO2   (2),
    biuInputIO3   (3),
    biuInputIO4   (4),
    biuInputIO5   (5),
    biuInputIO6   (6),
    biuInputIO7   (7),
    biuInputIO8   (8),
    biuInputIO9   (9),
    biuInputIO10  (10),
    biuInputIO11  (11),
    biuInputIO12  (12),
    biuInputIO13  (13),
    biuInputIO14  (14),
    biuInputIO15  (15),
    biuInputIO16  (16),
    biuInputIO17  (17),
    biuInputIO18  (18),
    biuInputIO19  (19),
    biuInputIO20  (20),
    biuInputIO21  (21),
    biuInputIO22  (22),
    biuInputIO23  (23),
    biuInputIO24  (24),
    biuInputIN1   (25),
    biuInputIN2   (26),
    biuInputIN3   (27),
    biuInputIN4   (28),
    biuInputIN5   (29),
    biuInputIN6   (30),
    biuInputIN7   (31),
    biuInputIN8   (32),
    biuInputOPT1  (33),
    biuInputOPT2  (34),
    biuInputOPT3  (35),
    biuInputOPT4  (36) }

--5.13.13.2 I/O Map TS2 BIU Output Pins
AscIOmapBIUoutputs ::= INTEGER {    -- Enumeration for NEMA TS2 BIU outputs (for each BIU)
    biuOutputO1   (1), 
    biuOutputO2   (2), 
    biuOutputO3   (3), 
    biuOutputO4   (4), 
    biuOutputO5   (5), 
    biuOutputO6   (6), 
    biuOutputO7   (7), 
    biuOutputO8   (8), 
    biuOutputO9   (9), 
    biuOutputO10  (10),
    biuOutputO11  (11),
    biuOutputO12  (12),
    biuOutputO13  (13),
    biuOutputO14  (14),
    biuOutputO15  (15),
    biuOutputIO1  (16),
    biuOutputIO2  (17),
    biuOutputIO3  (18),
    biuOutputIO4  (19),
    biuOutputIO5  (20),
    biuOutputIO6  (21),
    biuOutputIO7  (22),
    biuOutputIO8  (23),
    biuOutputIO9  (24),
    biuOutputIO10 (25),
    biuOutputIO11 (26),
    biuOutputIO12 (27),
    biuOutputIO13 (28),
    biuOutputIO14 (29),
    biuOutputIO15 (30),
    biuOutputIO16 (31),
    biuOutputIO17 (32),
    biuOutputIO18 (33),
    biuOutputIO19 (34),
    biuOutputIO20 (35),
    biuOutputIO21 (36),
    biuOutputIO22 (37),
    biuOutputIO23 (38),
    biuOutputIO24 (39) }

--5.13.14   I/O Map ATC Cabinet SIU Pins
ascIOmapSIU OBJECT IDENTIFIER ::= { ascIOmapping 14 }

--5.13.14.1 I/O Map ATC Cabinet SIU Input Pins
AscIOmapSIUinputs ::= INTEGER { -- Enumeration for ATC Cabinet SIU inputs (for each SIU)
    siuInputIO0  (1),
    siuInputIO1  (2),
    siuInputIO2  (3),
    siuInputIO3  (4),
    siuInputIO4  (5),
    siuInputIO5  (6),
    siuInputIO6  (7),
    siuInputIO7  (8),
    siuInputIO8  (9),
    siuInputIO9  (10),
    siuInputIO10 (11),
    siuInputIO11 (12),
    siuInputIO12 (13),
    siuInputIO13 (14),
    siuInputIO14 (15),
    siuInputIO15 (16),
    siuInputIO16 (17),
    siuInputIO17 (18),
    siuInputIO18 (19),
    siuInputIO19 (20),
    siuInputIO20 (21),
    siuInputIO21 (22),
    siuInputIO22 (23),
    siuInputIO23 (24),
    siuInputIO24 (25),
    siuInputIO25 (26),
    siuInputIO26 (27),
    siuInputIO27 (28),
    siuInputIO28 (29),
    siuInputIO29 (30),
    siuInputIO30 (31),
    siuInputIO31 (32),
    siuInputIO32 (33),
    siuInputIO33 (34),
    siuInputIO34 (35),
    siuInputIO35 (36),
    siuInputIO36 (37),
    siuInputIO37 (38),
    siuInputIO38 (39),
    siuInputIO39 (40),
    siuInputIO40 (41),
    siuInputIO41 (42),
    siuInputIO42 (43),
    siuInputIO43 (44),
    siuInputIO44 (45),
    siuInputIO45 (46),
    siuInputIO46 (47),
    siuInputIO47 (48),
    siuInputIO48 (49),
    siuInputIO49 (50),
    siuInputIO50 (51),
    siuInputIO51 (52),
    siuInputIO52 (53),
    siuInputIO53 (54),
    siuInputOPT1 (55),
    siuInputOPT2 (56),
    siuInputOPT3 (57),
    siuInputOPT4 (58) }

--5.13.14.2 I/O Map ATC Cabinet SIU Output Pins
AscIOmapSIUoutputs ::= INTEGER {    -- Enumeration for ATC Cabinet SIU outputs (for each SIU)
    siuOutputIO0  (1),
    siuOutputIO1  (2),
    siuOutputIO2  (3),
    siuOutputIO3  (4),
    siuOutputIO4  (5),
    siuOutputIO5  (6),
    siuOutputIO6  (7),
    siuOutputIO7  (8),
    siuOutputIO8  (9),
    siuOutputIO9  (10),
    siuOutputIO10 (11),
    siuOutputIO11 (12),
    siuOutputIO12 (13),
    siuOutputIO13 (14),
    siuOutputIO14 (15),
    siuOutputIO15 (16),
    siuOutputIO16 (17),
    siuOutputIO17 (18),
    siuOutputIO18 (19),
    siuOutputIO19 (20),
    siuOutputIO20 (21),
    siuOutputIO21 (22),
    siuOutputIO22 (23),
    siuOutputIO23 (24),
    siuOutputIO24 (25),
    siuOutputIO25 (26),
    siuOutputIO26 (27),
    siuOutputIO27 (28),
    siuOutputIO28 (29),
    siuOutputIO29 (30),
    siuOutputIO30 (31),
    siuOutputIO31 (32),
    siuOutputIO32 (33),
    siuOutputIO33 (34),
    siuOutputIO34 (35),
    siuOutputIO35 (36),
    siuOutputIO36 (37),
    siuOutputIO37 (38),
    siuOutputIO38 (39),
    siuOutputIO39 (40),
    siuOutputIO40 (41),
    siuOutputIO41 (42),
    siuOutputIO42 (43),
    siuOutputIO43 (44),
    siuOutputIO44 (45),
    siuOutputIO45 (46),
    siuOutputIO46 (47),
    siuOutputIO47 (48),
    siuOutputIO48 (49),
    siuOutputIO49 (50),
    siuOutputIO50 (51),
    siuOutputIO51 (52),
    siuOutputIO52 (53),
    siuOutputIO53 (54) }

--5.13.15   I/O Map Auxiliary Device Pins
ascIOmapAUX OBJECT IDENTIFIER ::= { ascIOmapping 15 }

--5.13.15.1 I/O Map Auxiliary Device Input Pins
AscIOmapAUXinputs ::= INTEGER { -- Enumeration for AUX inputs front panel AUX switch
    auxInputFPSwitch (1),       
    auxInputIO0      (2),
    auxInputIO1      (3),
    auxInputIO2      (4),
    auxInputIO3      (5),
    auxInputIO4      (6),
    auxInputIO5      (7),
    auxInputIO6      (8),
    auxInputIO7      (9) }

--5.13.15.2 I/O Map Auxiliary Device Outputs
AscIOmapAUXoutputs ::= INTEGER {    -- Enumeration for AUX outputs
    auxOutputIO0  (1),
    auxOutputIO1  (2),
    auxOutputIO2  (3),
    auxOutputIO3  (4),
    auxOutputIO4  (5),
    auxOutputIO5  (6),
    auxOutputIO6  (7),
    auxOutputIO7  (8) }

--5.14  SIU Port 1 Parameters
siuport1  OBJECT IDENTIFIER

    ::= { asc 14 }

-- This object is an identifier used to group all objects for support of ITS Cabinet V1 Section 4.7.14.7.1 SIU Port 1 Operation.
 
--5.14.1    Maximum SIU Port 1 Addresses
maxSIUPort1Addresses OBJECT-TYPE
    SYNTAX Integer32 (1..255)
    UNITS "address"
    MAX-ACCESS read-only
    STATUS current
    DESCRIPTION "<Definition> The Maximum Number of SIU Port 1 addresses this Actuated Controller Unit supports. This object indicates the maximum rows which shall appear in the siuPort1Table object.
    <Object Identifier> 1.3.6.1.4.1.1206.4.2.1.14.1
    <Object Type> S"
    ::= { siuport1 1 }
 
--5.14.2    SIU Port 1 Table
siuport1Table OBJECT-TYPE
    SYNTAX SEQUENCE OF SIUPort1Entry
    MAX-ACCESS not-accessible
    STATUS current
    DESCRIPTION "<Definition> A table containing Actuated Controller Unit port 1 parameters. The number of rows in this table is equal to maxSIUPort1Addresses object. Address 255 is reserved for the Broadcast All address.
    <TableType> static
    <Object Identifier> 1.3.6.1.4.1.1206.4.2.1.14.2"
    ::= { siuport1 2 }
 
siuport1Entry OBJECT-TYPE
    SYNTAX SIUPort1Entry
    MAX-ACCESS not-accessible
    STATUS current
    DESCRIPTION
    "<Definition> This object defines a conceptual row in the SIU Port 1 Table.
    <Object Identifier> 1.3.6.1.4.1.1206.4.2.1.14.2.1"
    INDEX { siuport1Number }
    ::= { siuport1Table 1 }

SIUPort1Entry ::= SEQUENCE {
    siuport1Number        Integer32,
    siuport1DevicePresent Integer32,
    siuport1Status        INTEGER}
 
--5.14.2.1  SIU Port 1 Number
siuport1Number OBJECT-TYPE
    SYNTAX Integer32 (1..255)
    UNITS "address"
    MAX-ACCESS not-accessible
    STATUS current
    DESCRIPTION "<Definition> The (SIU Port 1 address plus one) for objects in this row. This value shall not exceed the maxSIUPort1Addresses object value.
    <Object Identifier> 1.3.6.1.4.1.1206.4.2.1.14.2.1.1
    <Object Type> S"
    ::= { siuport1Entry 1 }

--5.15.2.2  SIU Port 1 Device Present
siuport1DevicePresent OBJECT-TYPE
    SYNTAX Integer32 (0..1)
    MAX-ACCESS read-write
    STATUS current
    DESCRIPTION "<Definition> This object is used to program the CU as to the presence or absence of a device for this SIU Port 1 address. The CU shall transmit Command Frames only to those devices that are present as determined by this programming.
True (one) - the device is present.
False (zero) - the device is not present.
    <Object Identifier> 1.3.6.1.4.1.1206.4.2.1.14.2.1.2
    <Object Type> C"
    REFERENCE "ATC 5301 Section 9"
    ::= { siuport1Entry 2 }

--5.14.2.3  SIU Port 1 Status
siuport1Status OBJECT-TYPE
    SYNTAX INTEGER { other (1),
                    online (2),
                    responseFault (3)}
    MAX-ACCESS read-only
    STATUS current
    DESCRIPTION "<Definition> This object indicates the communications status with the associated device:
other: This indicates that some other communications fault has been detected.
online: This indicates that at least five of the most recent 10 response transfers were received correctly.
responseFault: This indicates that more than 5 of the most recent 10 response transfers were received incorrectly.
    <Object Identifier> 1.3.6.1.4.1.1206.4.2.1.14.2.1.3
    <Object Type> S"
    ::= { siuport1Entry 3 }

--5.15  RSU Interface
ascRsuPort OBJECT IDENTIFIER
    ::= { asc 15 }

-- This defines a node to configure communications for a connected vehicle environment.

--5.15.1    RSU Interface Port
rsuCommPort OBJECT-TYPE
    SYNTAX Integer32 (0..255)
    MAX-ACCESS read-write
    STATUS current
    DESCRIPTION "<Definition> This object defines the ifIndex for a row in the ifTable and the commPortTable that identifies a communications port on the ASC that is used to exchange data with an RSU. A value of zero indicates that there is no RSU port or RSU communications is disabled. The value shall not exceed the value of maxCommPorts.
    <Object Identifier> 1.3.6.1.4.1.1206.4.2.1.15.1
    <Object Type> P"
    ::= { ascRsuPort 1 }
    
--5.15.2    Maximum Number of RSU Ports
maxRsuPorts OBJECT-TYPE
    SYNTAX Integer32 (1..16)
    UNITS "port"
    MAX-ACCESS read-only
    STATUS current
    DESCRIPTION "<Definition> This object contains the maximum number of logical RSU Ports this ASC supports. This object indicates the maximum rows which shall appear in the rsuPortTable object.
    <Object Identifier> 1.3.6.1.4.1.1206.4.2.1.15.2
    <Object Type> S"
    ::= { ascRsuPort 2 }

--5.15.3    Logical RSU Ports Table
rsuPortTable OBJECT-TYPE
    SYNTAX SEQUENCE OF RsuPortEntry 
    MAX-ACCESS not-accessible
    STATUS current
    DESCRIPTION "<Definition> This table contains configuration and status information for logical ports to communicate with RSUs. The number of rows in this table is equal to the maxRsuPorts object.
    <TableType> static
    <Object Identifier> 1.3.6.1.4.1.1206.4.2.1.15.3"
    ::= { ascRsuPort 3 }

rsuPortEntry OBJECT-TYPE
    SYNTAX RsuPortEntry
    MAX-ACCESS not-accessible
    STATUS current
    DESCRIPTION "<Definition> The configuration and status of a logical RSU port.
    <Object Identifier> 1.3.6.1.4.1.1206.4.2.1.15.3.1"
    INDEX  { rsuPortIndex }
    ::= { rsuPortTable 1 }

RsuPortEntry ::= SEQUENCE {
    rsuPortIndex         Integer32,
    rsuPortPointer       Integer32, --deprecated
    rsuPortName          SnmpAdminString,
    rsuPortPollingPeriod Integer32,
    rsuPortWatchdogTime  Integer32,
    rsuPortWatchdogTimer Integer32,
    rsuPortNumber        Integer32,
    rsuPortAddress       IpAddress }

--5.15.3.1  RSU Port Index
rsuPortIndex OBJECT-TYPE 
    SYNTAX Integer32 (1..16) 
    MAX-ACCESS not-accessible 
    STATUS current 
    DESCRIPTION "<Definition> This object provides the index into the RSU port table. This value shall not exceed the maxRsuPorts object value.
    <Object Identifier> 1.3.6.1.4.1.1206.4.2.1.15.3.1.1
    <Object Type> S" 
    ::= { rsuPortEntry 1 }

--5.16.3.2  RSU Logical Name Translation Entry Pointer
rsuPortPointer OBJECT-TYPE 
    SYNTAX Integer32 (1..255)
    MAX-ACCESS read-write 
    STATUS deprecated 
    DESCRIPTION "<Definition> This value is equal to the logicalNameTranslationIndex for the logical name translation table entry where logicalNameTranslationName holds the logical name and logicalNameTranslationNetworkAddress holds the IP address of the RSU port. This value shall not exceed the logicalNameTranslationTableMaxEntries object value.
    <Object Identifier> 1.3.6.1.4.1.1206.4.2.1.15.3.1.2
    <Object Type> P"
    ::= { rsuPortEntry 2 }

--5.15.3.2  RSU Port Name
rsuPortName OBJECT-TYPE 
    SYNTAX SnmpAdminString
    MAX-ACCESS read-write 
    STATUS current 
    DESCRIPTION "<Definition> A textual string describing the RSU or the location of the RSU. 
    <Object Identifier> 1.3.6.1.4.1.1206.4.2.1.15.3.1.3
    <Object Type> P" 
    ::= { rsuPortEntry 3 }

--5.15.3.3  RSU Interface Polling Period
rsuPortPollingPeriod OBJECT-TYPE
    SYNTAX Integer32 (0..65535)
    UNITS "millisecond"
    MAX-ACCESS read-write
    STATUS current
    DESCRIPTION "<Definition> This object defines the interval, in milliseconds, between polls on the port identified by this row. This object assumes that the CU behaves as the manager when exchanging data with an RSU. A value of zero indicates that polling is disabled. This object is not used if the CU is the SNMP agent between the ASC - RSU interface.
    <Object Identifier> 1.3.6.1.4.1.1206.4.2.1.15.3.1.4
    <Object Type> P"
    ::= { rsuPortEntry 4 }

--5.15.3.4  RSU Port Watchdog Time
rsuPortWatchdogTime OBJECT-TYPE
    SYNTAX Integer32 (0..65535)
    UNITS "millisecond"
    MAX-ACCESS read-write
    STATUS current
    DESCRIPTION "<Definition> This object defines the maximum time duration, in milliseconds, allowable without activity on the port identified by this row. If the amount of time that activity was last detected exceeds this value, then a RSU watchdog no activity fault alarm is SET. A value of zero disables the RSU Watchdog no activity fault alarm. This object is not used if rsuPortPollingPeriod is zero.
    <Object Identifier> 1.3.6.1.4.1.1206.4.2.1.15.3.1.5
    <Object Type> P"
    ::= { rsuPortEntry 5 }

--5.15.3.5  RSU Port Watchdog Timer
rsuPortWatchdogTimer OBJECT-TYPE
    SYNTAX Integer32 (0..65535)
    UNITS "millisecond"
    MAX-ACCESS read-only
    STATUS current
    DESCRIPTION "<Definition> This object defines the watchdog time, in milliseconds, which is the amount of time since activity was last detected on the port identified by this row (rsuPortIndex). Activity is defined as any valid data object received on the port. If this object exceeds rsuPortWatchdogTime, then a RSU watchdog no activity fault is reported. This object is not used if rsuPortPollingPeriod is 0.
    <Object Identifier> 1.3.6.1.4.1.1206.4.2.1.15.3.1.6
    <Object Type> S"
    ::= { rsuPortEntry 6 }

--5.15.3.6  RSU Port Number
rsuPortNumber OBJECT-TYPE
    SYNTAX Integer32 (0..65535)
    MAX-ACCESS read-write
    STATUS current
    DESCRIPTION "<Definition> This object defines the port number on the RSU for the ASC to send data to. An object value of 0 indicates communication to this port is disabled. 
    <Object Identifier> 1.3.6.1.4.1.1206.4.2.1.15.3.1.7
    <Object Type> P"
    DEFVAL { 0 }
    ::= { rsuPortEntry 7 }

--5.15.3.7  RSU Port Address
rsuPortAddress OBJECT-TYPE
    SYNTAX IpAddress
    MAX-ACCESS read-write
    STATUS current
    DESCRIPTION "<Definition> This object defines the IP address of the RSU for this port.
    
    NTCIP 1103 was previously used to identify the IP address in NTCIP 1202 v03. 

    <Object Identifier> 1.3.6.1.4.1.1206.4.2.1.15.3.1.8
    <Object Type> P"
    ::= { rsuPortEntry 8 }

--5.16  ASC SPaT
ascSpat OBJECT IDENTIFIER
    ::= { asc 16 }

-- This defines a node to support signal phase and timing objects for a connected vehicle environment.

--5.16.1    SPaT Data Timestamp
spatTimestamp OBJECT-TYPE
    SYNTAX OCTET STRING (SIZE(0 | 5))
    MAX-ACCESS read-only
    STATUS current
    DESCRIPTION "<Definition> A 5-byte value representing the time of day the SPAT data is generated by the CU. The 5 bytes are:
    Byte 1: hours (0..23)
    Byte 2: minutes (0..59)
    Byte 3: seconds (0..60). 60 is used to support leap seconds.
    Byte 4-5: milliseconds (0..999)
    <Object Identifier> 1.3.6.1.4.1.1206.4.2.1.16.1
    <Object Type> S"
    DEFVAL { "" }
    ::= { ascSpat 1 }

--5.17.2    SPaT Enabled Lanes Command
spatEnabledLanesCommand OBJECT-TYPE
    SYNTAX OCTET STRING
    MAX-ACCESS read-write
    STATUS deprecated
    DESCRIPTION "<Definition> To support SAE J2735, this object is used to establish the Enabled lanes for the device to be broadcast in a SPAT message. Each octet within the octet string contains the mapLaneIndex(s) (binary value) in the MAP plan data configuration that is broadcast to be ACTIVE.

An octet string of SIZE(1) with A value of zeroxFF indicates that the device shall cancel this command and shall revert back to the Enabled lanes defined by  enabledlaneconcurrency for the current time base action. Otherwise, the Enabled lanes defined is this command shall override the Enabled lanes defined in enabledlaneconcurrency.

If the commanded set if Enabled lanes is valid, the new set of Enabled lanes will be broadcast at the top of the next cycle. If an unsupported / invalid set of Enabled lanes is called, then the spatPortStatus object shall be SET to enabledLanesError(5) for all valid entries in the spatPortTable.
    <Object Identifier> 1.3.6.1.4.1.1206.4.2.1.16.2
    <Object Type> P"
    REFERENCE "SAE J2735 DF_EnabledLaneList"
    ::= { ascSpat 2 }

--5.16.2    SPaT Enabled Lanes Concurrency Table
spatEnabledLanesConcurrencyTable OBJECT-TYPE
    SYNTAX SEQUENCE OF SpatEnabledLanesConcurrencyEntry
    MAX-ACCESS not-accessible
    STATUS current
    DESCRIPTION "<Definition> A table containing the revocable lanes that are allowed to be concurrently ACTIVE. The number of rows in this table is equal to the value of maxEnabledLanesConcurrency.
    <TableType> static
    <Object Identifier> 1.3.6.1.4.1.1206.4.2.1.16.3"
    ::= { ascSpat 3 }

spatEnabledLanesConcurrencyEntry OBJECT-TYPE
    SYNTAX SpatEnabledLanesConcurrencyEntry
    MAX-ACCESS not-accessible
    STATUS current
    DESCRIPTION "<Definition> The allowable lanes that may be ACTIVE concurrently.
    <Object Identifier> 1.3.6.1.4.1.1206.4.2.1.16.3.1"
    INDEX  { enabledLaneIndex }
    ::= { spatEnabledLanesConcurrencyTable 1 }

SpatEnabledLanesConcurrencyEntry::= SEQUENCE {
    enabledLaneIndex        Integer32,
    enabledLaneConcurrency  OCTET STRING }

--5.16.3.1  Enabled Lane Index
enabledLaneIndex OBJECT-TYPE
    SYNTAX Integer32 (1..255)
    MAX-ACCESS not-accessible
    STATUS current
    DESCRIPTION "<Definition> The number for objects in this row. This value shall not exceed the maxEnabledLanesConcurrency object value.
    <Object Identifier> 1.3.6.1.4.1.1206.4.2.1.16.3.1.1"
    ::= { spatEnabledLanesConcurrencyEntry 1 }

--5.16.3.2  Enabled Lane Concurrency
enabledLaneConcurrency OBJECT-TYPE
    SYNTAX OCTET STRING
    MAX-ACCESS read-write
    STATUS current
    DESCRIPTION "<Definition> Each octet contains a revocable lane identifier that may be ACTIVE concurrently. The value could be a single octet. This object indicates a set of revocable lanes that may be simultaneously enabled. Revocable lanes are identified in the MAP message for the intersection.
    <Object Identifier> 1.3.6.1.4.1.1206.4.2.1.16.3.1.2
    <Object Type> P"
    REFERENCE "SAE J2735 DF_EnabledLaneList"
    ::= { spatEnabledLanesConcurrencyEntry 2 }

--5.16.3    SPaT Message Options
spatOptions OBJECT-TYPE
    SYNTAX Integer32 (0..255)
    MAX-ACCESS read-write
    STATUS current
    DESCRIPTION "<Definition> Optional SPAT functions ( 0 = False/Disabled, 1 = True/Enabled)
    Bit 7: Reserved.
    Bit 6: Reserved.
    Bit 5: Reserved.
    Bit 4: Reserved.
    Bit 3: Reserved.
    Bit 2: MAP Validity. Indicates if the MAP data message broadcasted by the RSU is valid (1) or invalid (0). When this bit is one, the MAP Message broadcasted by the CV Application Process is considered valid. When this bit is 0, then the MAP message broadcasted by the RSU is considered invalid and should not be used except for test purposes.
    Bit 1: SPaT Validity. Indicates if the SPaT data for this CU is valid (1) or invalid (0). When this bit is one, the SPaT data provided by the controller is considered valid. When this bit is 0, then the SPaT data provided by the controller is considered invalid and should not be used except for test purposes.  
    Bit 0: Enabled SPAT. Provides a means to enable the CU to provide SPAT data to a management station or a RSU.
    <Object Identifier> 1.3.6.1.4.1.1206.4.2.1.16.4
    <Object Type> P"
    ::= { ascSpat 4 }

--5.16.4    SPaT RSU Ports Table
spatPortTable OBJECT-TYPE
    SYNTAX SEQUENCE OF SpatPortEntry 
    MAX-ACCESS not-accessible
    STATUS current
    DESCRIPTION "<Definition> This table contains configuration and status information for exchanging SPAT information with RSUs. The number of rows in this table is equal to the maxRsuPorts object.
    <TableType> static
    <Object Identifier> 1.3.6.1.4.1.1206.4.2.1.16.5"
    ::= { ascSpat 5 }

spatPortEntry OBJECT-TYPE
    SYNTAX SpatPortEntry
    MAX-ACCESS not-accessible
    STATUS current
    DESCRIPTION "<Definition> The configuration and status to exchange SPAT data with a logical RSU port.
    <Object Identifier> 1.3.6.1.4.1.1206.4.2.1.16.5.1"
    INDEX  { rsuPortIndex }
    ::= { spatPortTable 1 }

SpatPortEntry ::= SEQUENCE {
    spatPortOptions           Integer32,
    spatPortStatus            INTEGER,
    spatPortMapActivationCode MapActivationCode }

--5.16.4.1  SPaT Port Options
spatPortOptions OBJECT-TYPE
    SYNTAX Integer32 (0..255)
    MAX-ACCESS read-write
    STATUS current
    DESCRIPTION "<Definition> Optional SPAT functions for this SPAT port(0 = False/Disabled, 1 = True/Enabled)
    Bit 7: Reserved
    Bit 6: Reserved
    Bit 5: Reserved
    Bit 4: Reserved
    Bit 3: Reserved
    Bit 2: MAP Validity. Indicates if the MAP data message broadcasted by the RSU on this RSU port is valid (1) or invalid (0). When this bit is one, the MAP Message broadcasted by the CV Application Process is considered valid. When this bit is 0, then the MAP message broadcasted by the RSU is considered invalid and should not be used except for test purposes.
    Bit 1: SPAT Validity. Indicates if the SPaT data on this RSU port is valid (1) or invalid (0). When this bit is one, the SPaT data provided by the controller is considered valid. When this bit is 0, then the SPaT data provided by the controller is considered invalid and should not be used except for test purposes. 
    Bit 0: Enabled SPAT. Provides a means to enable the CU to exchange SPAT data on this RSU port.  
    <Object Identifier> 1.3.6.1.4.1.1206.4.2.1.16.5.1.1
    <Object Type> P"
    ::= { spatPortEntry 1 }

--5.16.4.2  SPaT Port Status
spatPortStatus OBJECT-TYPE
    SYNTAX INTEGER { other(1),
                 disabled(2),
                 normal(3),
                 mapError(4),
                 enabledLanesError(5) }
    MAX-ACCESS read-only
    STATUS current
    DESCRIPTION "<Definition> The status for exchanging SPAT data for this RSU port.
    other: A status not defined by this standard.
    disabled: The capability to provide SPAT data is disabled.
    normal: The CU is providing SPAT data.
    mapError: The CU has stopped providing SPAT data because of an inconsistency in the spatPortMapActivationCode.
    enabledLanesError: The CU has stopped providing SPAT data because of an inconsistency error with the SPAT enabled lanes concurrency table (spatEnabledLanesConcurrencyTable). Note: Bit 13 in the spatStatus2 is also enabled.
    <Object Identifier> 1.3.6.1.4.1.1206.4.2.1.16.5.1.2
    <Object Type> S"
    ::= { spatPortEntry 2 }

--5.16.4.3  SPaT Port MAP Activation Code
spatPortMapActivationCode OBJECT-TYPE
    SYNTAX MapActivationCode
    MAX-ACCESS read-write
    STATUS current
    DESCRIPTION "<Definition> Represents the current mapActivationCode for this RSU port that the signal patterns on the CU are programmed for. The spatPortMapActivationCode value in this row should match the mapActivatePlan value for the RSU on this RSU port.
This object allows the CU to compare and confirm that the signal phase and timing data matches the MAP data that may be broadcast by the RSU.
    <Object Identifier> 1.3.6.1.4.1.1206.4.2.1.16.5.1.3
    <Object Type> P"
    ::= { spatPortEntry 3 }

--5.17.6    Current Tick Counter
ascCurrentTick OBJECT-TYPE
    SYNTAX Integer32 (0..36000)
    UNITS "decisecond"
    MAX-ACCESS read-only
    STATUS deprecated
    DESCRIPTION "<Definition> This object is a counter of the number of elapsed ASC traffic processing ticks. The value is incremented by 1 (decisecond) every time the ASC completes its tenth of a second processing and commits a new set of IO signal states. 

The object is represented as a rolling counter with a zero representing the top of the hour. If the counter were to be incremented beyond 35999 the value shall roll over back to 0. Values equal to or greater than 36000 are reserved.
    <Object Identifier> 1.3.6.1.4.1.1206.4.2.1.16.6
    <Object Type> S"
    ::= { ascSpat 6 }

--5.17.7    Current Tick Counter - Milliseconds
ascCurrentTickMsOffset OBJECT-TYPE
    SYNTAX Integer32 (0..99)
    UNITS "millisecond"
    MAX-ACCESS read-only
    STATUS deprecated
    DESCRIPTION "<Definition> This object reflects the elapsed milliseconds within the current ASC traffic processing tick at the moment this object was encoded and transmitted. The main purpose of this object is to provide millisecond accuracy when calculating the future time points defined in the signalStatusTable2. It is important to note that this object is intended to be used with a remote NTCIP manager polling or issuing GET requests on the ascCurrentTick2 object. If ascCurrentTick2 is pushed, SET, or otherwise event driven then the ascCurrentTickMsOffset will not be useful as the ascCurrentTick2 object will be transmitted exactly on tick boundaries (ie always when ascCurrentTickMsOffset is 0). If an NTCIP manager is polling the ASC for the tick count it is recommended that the manager request both ascCurrentTick2 and ascCurrentMsTickOffset in a combined atomic varbind PDU to guarantee consistency between both objects.
    <Object Identifier> 1.3.6.1.4.1.1206.4.2.1.16.7
    <Object Type> S"
    ::= { ascSpat 7 }

--5.16.5    Current Tick Counter
ascCurrentTick2 OBJECT-TYPE
    SYNTAX Integer32 (0..36111)
    UNITS "decisecond"
    MAX-ACCESS read-only
    STATUS current
    DESCRIPTION "<Definition> This object is a counter of the number of elapsed ASC traffic processing ticks. The value is incremented by 1 (decisecond) every time the ASC completes its tenth of a second processing and commits a new set of IO signal states. 

The object is represented as a rolling counter with a zero representing the top of the hour. If the counter were to be incremented beyond 35999, unless a leap seconds occur, the value shall roll over back to 0. The values 36000..36009 are used when a leap second occurs. The values 36010..36110 are reserved for future use. 36111 is to be used when the value is undefined or unknown.
See Annex F.3.3.1 for additional guidance.
    <Object Identifier> 1.3.6.1.4.1.1206.4.2.1.16.8
    <Object Type> S"
    REFERENCE "SAE J2735 DE_TimeMark"
    DEFVAL { 36111 }
    ::= { ascSpat 8 }

--5.16.6    Maximum Signal Groups
maxSignalGroups OBJECT-TYPE
    SYNTAX Integer32 (1..255)
    UNITS "signalGroupID"
    MAX-ACCESS read-only
    STATUS current
    DESCRIPTION "<Definition> This object indicates the maximum rows which shall appear in the signalGroupEntryTable object.
    <Object Identifier> 1.3.6.1.4.1.1206.4.2.1.16.9
    <Object Type> S"
    ::= { ascSpat 9 }

--5.16.7   Signal Group Entry Table
signalGroupEntryTable OBJECT-TYPE
    SYNTAX SEQUENCE OF SignalGroupEntry
    MAX-ACCESS not-accessible
    STATUS current
    DESCRIPTION "<Definition> This table contains configuration information for a signalGroupID at a signalized intersection. The number of rows in this table is equal to the maxSignalGroups object. See Annex F.3.3.5.1 for additional guidance.
    <TableType> static
    <Object Identifier> 1.3.6.1.4.1.1206.4.2.1.16.10"
    ::= { ascSpat 10 }

signalGroupEntry OBJECT-TYPE
    SYNTAX SignalGroupEntry
    MAX-ACCESS not-accessible
    STATUS current
    DESCRIPTION "<Definition> Parameters for specific signal groups at an intersection. 
    <Object Identifier> 1.3.6.1.4.1.1206.4.2.1.16.10.1"
    INDEX  { signalGroupEntryNumber }
    ::= { signalGroupEntryTable 1 }

SignalGroupEntry ::= SEQUENCE {
    signalGroupEntryNumber             Integer32,
    signalGroupIntersection            Integer32,
    signalGroupID                      Integer32,
    signalGroupControlSource           Integer32,
    signalGroupControlType             INTEGER,
    signalGroupGreenType               INTEGER,
    signalGroupRedType                 INTEGER,
    signalGroupPermissiveControlSource Integer32,
    signalGroupPermissiveControlType   Integer32,
    signalGroupEnabledLanes            Integer32 }

--5.16.7.1 Signal Group Entry Number
signalGroupEntryNumber OBJECT-TYPE
    SYNTAX Integer32 (1..255)
    MAX-ACCESS not-accessible
    STATUS current
    DESCRIPTION "<Definition> The number for objects in this row. This value shall not exceed the maxSignalGroups object value.
    <Object Identifier> 1.3.6.1.4.1.1206.4.2.1.16.10.1.1"
    ::= { signalGroupEntry 1 }

--5.16.7.2 Signal Group Intersection
signalGroupIntersection OBJECT-TYPE
    SYNTAX Integer32 (0..65535)
    MAX-ACCESS read-write
    STATUS current
    DESCRIPTION "<Definition> The number is used to uniquely define an intersection within the region. A value of zero indicates that the row is disabled and all other values in the row are not valid.
    <Object Identifier> 1.3.6.1.4.1.1206.4.2.1.16.10.1.2
    <Object Type> P"
    REFERENCE "SAE J2735 DE_IntersectionID"
    DEFVAL { 0 }
    ::= { signalGroupEntry 2 }

--5.16.7.3 Signal Group Identifier
signalGroupID OBJECT-TYPE
    SYNTAX Integer32 (0..255)
    MAX-ACCESS read-write
    STATUS current
    DESCRIPTION "<Definition> The number used to map between a movement phase state (and its timings) in the CU and movements defined in a MAP message for the intersection. A value of 255 is reserved to indicate a permanent green movement state. A value of zero indicates not available or not known.
    <Object Identifier> 1.3.6.1.4.1.1206.4.2.1.16.10.1.3
    <Object Type> P"
    REFERENCE "SAE J2735 DE_SignalGroupID"
    DEFVAL { 255 }
    ::= { signalGroupEntry 3 }

--5.16.7.4 Signal Group Control Source Parameter
signalGroupControlSource OBJECT-TYPE
    SYNTAX Integer32 (0..255)
    MAX-ACCESS read-write
    STATUS current
    DESCRIPTION "<Definition> This object defines which Phase or Overlap controls the signal group. The value shall not exceed maxPhases or maxOverlaps as determined by the signalGroupControlType object:
    Value 00 = No Control (Not In Use)
    Value 01 = Phase 01 or Overlap A
    Value 02 = Phase 02 or Overlap B
    ||
    Value 15 = Phase 15 or Overlap O
    Value 16 = Phase 16 or Overlap P
    etc.
    <Object Identifier> 1.3.6.1.4.1.1206.4.2.1.16.10.1.4
    <Object Type> P"
    DEFVAL { 0 }
    ::= { signalGroupEntry 4 }

--5.16.7.5 Signal Group Control Type Parameter
signalGroupControlType OBJECT-TYPE
    SYNTAX INTEGER { other (1),
                 phaseVehicle (2),
                 phasePedestrian (3), 
                 overlap (4),
                 pedOverlap (5),
                 queueJump (6) }
    MAX-ACCESS read-write
    STATUS current
    DESCRIPTION "<Definition> This object defines the type of control for the signal group:
other: The signal group is not controlled by a type defined by this standard. Per NTCIP 8004 v02, an attempt to write a value of 'other' shall return a badValue error. A user- or manufacturer-specific object is permitted to extend the possible states.
phaseVehicle: The signal group is for a vehicle phase, bicycle phase, or transit phase.
phasePedestrian: The signal group is for a pedestrian phase.
overlap: The signal group is for an overlap for vehicles, bicycles, or transit.
pedOverlap: The signal group is for a pedestrian overlap.
queueJump: The signal group is for a queue jump, typically transit priority.
    <Object Identifier> 1.3.6.1.4.1.1206.4.2.1.16.10.1.5
    <Object Type> P"
    ::= { signalGroupEntry 5 }

--5.16.7.6 Signal Group Green Type
signalGroupGreenType OBJECT-TYPE
    SYNTAX INTEGER { other (1),
                 preMovement (2),
                 permissiveMovementAllowed (3),
                 protectedMovementAllowed (4),
                 protectedPermissive (5)}
    MAX-ACCESS read-write
    STATUS current
    DESCRIPTION "<Definition> This object defines the type of Green to be indicated for the signal group in a SPaT message:
other: The signal group green type is not defined by this standard. Per NTCIP 8004 v02, an attempt to write a value of 'other' shall return a badValue error. A user- or manufacturer-specific object is permitted to extend the possible states.
preMovement: Prepare to proceed. Not common in the United States.
permissiveMovementAllowed: The signal group is a permissive green and may have to yield to conflicting traffic.
protectedMovementAllowed: The signal group is a protected green and has the right-of-way.
protectedPermissive: Indicates that the movement for the signal group can be protected during some portions of the cycle and permissive during other portions of the cycle. The signalGroupPermissiveControlSource and signalGroupPermissiveControlType objects determine if the movement is protected or permissive.
    <Object Identifier> 1.3.6.1.4.1.1206.4.2.1.16.10.1.6
    <Object Type> P"
    REFERENCE "SAE J2735 DE_MovementPhaseState"
    DEFVAL { 3 }
    ::= { signalGroupEntry 6 }

--5.16.7.7 Signal Group Red Type
signalGroupRedType OBJECT-TYPE
    SYNTAX INTEGER { other (1),
                 stopThenProceed (2),
                 stopAndRemain (3)}
    MAX-ACCESS read-write
    STATUS current
    DESCRIPTION "<Definition> This object defines the type of Red to be indicated for the signal group in a SPaT message:
other: The signal group red type is not defined by this standard. Per NTCIP 8004 v02, an attempt to write a value of 'other' shall return a badValue error. A user- or manufacturer-specific object is permitted to extend the possible states.
stopThenProceed: Indicates the vehicle must stop at the stop line when the signal indication is red. It may then proceed if it is safe.
stopAndRemain: Indicates the traveler must stop and remain at the stop line when the signal indication is red. It may not proceed. 
    <Object Identifier> 1.3.6.1.4.1.1206.4.2.1.16.10.1.7
    <Object Type> P"
    REFERENCE "SAE J2735 DE_MovementPhaseState"
    DEFVAL { 3 }
    ::= { signalGroupEntry 7 }

--5.16.7.8 Permissive Signal Group Control Source Parameter
signalGroupPermissiveControlSource OBJECT-TYPE
    SYNTAX Integer32 (0..255)
    MAX-ACCESS read-write
    STATUS current
    DESCRIPTION "<Definition> If signalGroupGreenType is protectedPermissive(5) for the row, this object in combination with signalGroupPermissiveControlType identifies which phase or overlap controls the permissive portion of the protected-permissive movement. If signalGroupGreenType is any value other than protectedPermissive(5), then this object is ignored. The value shall not exceed maxPhases or maxOverlaps as determined by the signalGroupPermissiveControlType object:
    Value 00 = No Control  (Not In Use)
    Value 01 = Phase 01 or Overlap A
    Value 02 = Phase 02 or Overlap B
    ||
    Value 15 = Phase 15 or Overlap O
    Value 16 = Phase 16 or Overlap P
    etc.
    <Object Identifier> 1.3.6.1.4.1.1206.4.2.1.16.10.1.8
    <Object Type> P"
    DEFVAL { 0 }
    ::= { signalGroupEntry 8 }

--5.16.7.9 Permissive Signal Group Control Type Parameter
signalGroupPermissiveControlType OBJECT-TYPE
    SYNTAX INTEGER { other (1),
                 none (2),
                 phaseVehicle (3),
                 phasePedestrian (4), 
                 overlap (5),
                 pedOverlap (6),
                 queueJump (7) }
    MAX-ACCESS read-write
    STATUS current
    DESCRIPTION "<Definition> If signalGroupGreenType is protectedPermissive(5) for the row, this object in combination with signalGroupPermissiveControlSource identifies which phase or overlap controls the permissive portion of the protected-permissive movement. If signalGroupGreenType is any value other than protectedPermissive(5), then this object is ignored.
    other: The signal group is not controlled by a type defined by this standard. Per NTCIP 8004 v02, an attempt to write a value of 'other' shall return a badValue error. A user- or manufacturer-specific object is permitted to extend the possible states.
    none: The signal group is not dependent on another phase nor overlap.
    phaseVehicle: The signal group is dependent on a vehicle phase, bicycle phase, or transit phase.
    phasePedestrian: The signal group is dependent on a pedestrian phase.
    Overlap: The signal group is dependent on an overlap for vehicles, bicycles, or transit.
    pedOverlap: The signal group is dependent on a pedestrian overlap.
    queueJump: The signal group is dependent on a queue jump, typically transit priority.
    <Object Identifier> 1.3.6.1.4.1.1206.4.2.1.16.10.1.9
    <Object Type> P"
    DEFVAL { 2 }
    ::= { signalGroupEntry 9 }

--5.16.7.10    Signal Group Enabled Lane
signalGroupEnabledLanes OBJECT-TYPE
    SYNTAX Integer32 (0..255)
    MAX-ACCESS read-write
    STATUS current
    DESCRIPTION "<Definition> The value is equal to the enabledLaneIndex in the spatEnabledLanesConcurrencyTable. Each octet within the octet string for enabledLaneConcurrency in that row contains the (revocable) lane number that must be enabled for this signal group to be enabled. If all specified lanes are enabled, then this signal group is enabled and in use. Otherwise, the signal group is disabled and not used. A value of zero indicates that this signal group is not dependent on a revocable lane. This value shall not exceed the maxEnabledLanesConcurrency object value.

    This object was named signalGroupLane in NTCIP 1202 v03
    <Object Identifier> 1.3.6.1.4.1.1206.4.2.1.16.10.1.10
    <Object Type> P"
    DEFVAL { 0 }
    ::= { signalGroupEntry 10 }

--5.16.8   Maximum Agency Signal State Entries
maxAgencySignalStates OBJECT-TYPE
    SYNTAX Integer32 (3..255)
    MAX-ACCESS read-only
    STATUS current
    DESCRIPTION "<Definition> This object indicates the maximum rows which shall appear in the agencySignalStateTable object.
    <Object Identifier> 1.3.6.1.4.1.1206.4.2.1.16.11
    <Object Type> S"
    ::= { ascSpat 11 }

--5.16.9   Agency Signal State Table
agencySignalStateTable OBJECT-TYPE
    SYNTAX SEQUENCE OF AgencySignalStateEntry
    MAX-ACCESS not-accessible
    STATUS current
    DESCRIPTION "<Definition> This table is a lookup table to determine the movement phase state for a signal group. See Annex F.3.3.5.2 for additional guidance and see Figure 15 for the default values for the table.
    <Object Identifier> 1.3.6.1.4.1.1206.4.2.1.16.12"
    ::= { ascSpat 12 }

agencySignalStateEntry OBJECT-TYPE
    SYNTAX AgencySignalStateEntry
    MAX-ACCESS not-accessible
    STATUS current
    DESCRIPTION "<Definition> This table defines the signal state to provide for a signal group in the SPaT message based upon the parameters set in the signalGroupEntryTable.
    <Object Identifier> 1.3.6.1.4.1.1206.4.2.1.16.12.1"
    INDEX  { agencySignalStateNumber }
    ::= { agencySignalStateTable 1 }

AgencySignalStateEntry ::= SEQUENCE {
    agencySignalStateNumber      Integer32,
    agencySignalStateColor       INTEGER,
    agencySignalStateControlType INTEGER,
    agencySignalStateOptions     Integer32,
    agencySignalStateValue       INTEGER }

--5.16.9.1 Agency Signal State Entry Number
agencySignalStateNumber OBJECT-TYPE
    SYNTAX Integer32 (1..255)
    MAX-ACCESS not-accessible
    STATUS current
    DESCRIPTION "<Definition> The number for objects in this row. This value shall not exceed the maxAgencySignalStates object value.
    <Object Identifier> 1.3.6.1.4.1.1206.4.2.1.16.12.1.1"
    ::= { agencySignalStateEntry 1 }

--5.16.9.2 Agency Signal State Color
agencySignalStateColor OBJECT-TYPE
    SYNTAX INTEGER { other (1),
                 red (2),
                 yellow (3),
                 green (4), 
                 dark (5),
                 flashingRed (6),
                 flashingYellow (7) }
    MAX-ACCESS read-write
    STATUS current
    DESCRIPTION "<Definition> This object indicates the color of the phase or overlap that the signal group is associated with to determine a signal state to broadcast in a SPaT message. 

    other: The phase or overlap is not defined by this standard.  Per NTCIP 8004 v02, an attempt to write a value of 'other' shall return a badValue error. A manufacturer-specific object is permitted to extend the possible states.
    red: The phase or overlap is red. If the agencySignalStateControlType object is pedestrian(3), this value indicates a Steady Don't Walk.
    yellow: The phase or overlap is yellow.
    green: The phase or overlap is green. If the agencySignalStateControlType object is pedestrian(3), this value indicates a Walk.
    dark: The phase or overlap is dark.
    flashingRed: The phase or overlap is Flashing Red. If the agencySignalStateControlType object is pedestrian(3), this value indicates a Flashing Don't Walk.
    flashingYellow: The phase or overlap is Flashing Yellow.
    <Object Identifier> 1.3.6.1.4.1.1206.4.2.1.16.12.1.2
    <Object Type> P"
    ::= { agencySignalStateEntry 2 }

--5.16.9.3 Agency Signal State Control Type
agencySignalStateControlType OBJECT-TYPE
    SYNTAX INTEGER { other (1),
                    vehicle (2),
                    pedestrian (3) }
    MAX-ACCESS read-write
    STATUS current
    DESCRIPTION "<Definition> This object defines the type of control for the signal group (Vehicle Phase, Pedestrian Phase, Overlap or Pedestrian Overlap) to be used to determine the movement phase state to broadcast in a SPaT message:
other: The signal group is not defined by this standard. Per NTCIP 8004 v02, an attempt to write a value of 'other' shall return a badValue error. A user- or manufacturer-specific object is permitted to extend the possible states.
vehicle: The signal group is is configured in the signalGroupEntryTable with a control type of phaseVehicle (3) or overlap (5) or queueJump (7).
pedestrian: The signal group is configured in the signalGroupEntryTable with a control type of phasePedestrian (4) or pedOverlap (6).
    <Object Identifier> 1.3.6.1.4.1.1206.4.2.1.16.12.1.3
    <Object Type> P"
    ::= { agencySignalStateEntry 3 }

--5.16.9.4 Additional Parameters for Determining Signal State
agencySignalStateOptions OBJECT-TYPE
    SYNTAX Integer32 (0..65535)
    MAX-ACCESS read-write
    STATUS current
    DESCRIPTION "<Definition> Additional parameters for determining the movement phase state to broadcast in a SPaT message ( 0 = FALSE/Disabled, 1 = TRUE/Enabled )
Bit 15: Reserved
Bit 14: Reserved
Bit 13: Reserved
Bit 12: Reserved
Bit 11: Reserved
Bit 10: Reserved
Bit 9: Permissive Flashing Red -The signalGroupPermissiveControlSource / signalGroupPermissiveControlType indication is Flashing Red.
Bit 8: Permissive Flashing Yellow -The signalGroupPermissiveControlSource / signalGroupPermissiveControlType indication is Flashing Yellow. 
Bit 7: Permissive Green -The signalGroupPermissiveControlSource / signalGroupPermissiveControlType indication is Green.
Bit 6: Permissive Yellow -The signalGroupPermissiveControlSource / signalGroupPermissiveControlType indication is Yellow.
Bit 5: Permissive Red - The signalGroupPermissiveControlSource / signalGroupPermissiveControlType indication is Red.
Bit 4: Protected Green - If Bit 1 is TRUE, the signal group is configured in the signalGroupEntryTable with a signalGroupGreenType of protectedMovementAllowed (4) or protectedPermissive (5).
Bit 3: Permissive Green - If Bit 1 is TRUE, the signal group is configured in the signalGroupEntryTable with a signalGroupGreenType of permissiveMovementAllowed (3) or protectedPermissive (5).
Bit 2: preMovement Green - If Bit 1 is TRUE, the signal group is configured in the signalGroupEntryTable with a signalGroupGreenType is preMovement (2). Not used in the US. 
Bit 1: stopAndRemain - If Bit 1 is TRUE, the signal group is configured in the signalGroupEntryTable with a signalGroupRedType of stopAndRemain (3).
Bit 0: stopThenProceed - If Bit 1 is TRUE, the signal group is configured in the signalGroupEntryTable with a signalGroupRedType of stopThenProceed (2).

If both Bits 0 and 1 are FALSE, then the signalGroupRedType is not applicable. Bits 0 and 1 cannot be both TRUE. A SET of both bits 0 and 1 to TRUE shall result return a badValue(3) error.

If both Bits 3 and 4 are FALSE, then the signalGroupGreenType is not applicable. If only Bit 3 is TRUE, then the signalGroupGreenType for the the signal group in the signalGroupEntryTable is permissiveMovementAllowed (3). If only Bit 4 is TRUE, then the signalGroupGreenType for the signal group in the signalGroupEntryTable is protectedMovementAllowed (4). If both Bits 3 and 4 are TRUE, that indicates the signalGroupGreenType is protectedPermissive and the signal indication of signalGroupPermissiveControlType and signalGroupPermissiveControlSource determines if the signal green type is permissiveMovementAllowed or protectedMovementAllowed.

Bits 5-9 determine what signal indication(s) of the signalGroupPermissiveControlType / signalGroupPermissiveControlSource makes the movement permissive. If Bits 5-9 are all TRUE, then ANY signal indication of the signalGroupPermissiveControlType / signalGroupPermissiveControlSource determines if the movement is permissive. If Bits 5-9 are all FALSE, then the color of the signalGroupPermissiveControlType / signalGroupPermissiveControlSource is not applicable.
See Annex F.3.3.5.2 and F.3.3.5.3 for additional guidance.
    <Object Identifier> 1.3.6.1.4.1.1206.4.2.1.16.12.1.4
    <Object Type> P"
    ::= { agencySignalStateEntry 4 }

--5.16.9.5 Agency Signal State Indication
agencySignalStateValue OBJECT-TYPE
    SYNTAX INTEGER { other (1),
                 unavailable (2),
                 dark (3), 
                 stopThenProceed (4),
                 stopAndRemain (5),
                 preMovement (6),
                 permissiveMovementAllowed (7),
                 protectedMovementAllowed (8),
                 permissiveClearance (9),
                 protectedClearance (10),
                 cautionConflictingTraffic (11) }
    MAX-ACCESS read-write
    STATUS current
    DESCRIPTION "<Definition> This object indicates the movement phase state to be broadcasted in a SPaT message. 
    other: The movement phase state is not defined by this standard.
    unavailable: The state of the movement is unknown or an error occurred.
    dark: The signal head is dark (unlit)
    stopThenProceed: Indicates the vehicle must stop at the stop line. It may proceed if it is safe.
    stopAndRemain: Indicates the vehicle must stop at the stop line. It may not proceed.
    preMovement: Prepare to proceed.
    permissiveMovementAllowed: Indicates a permissive green.
    protectedMovementAllowed: Indicates a protected green (a steady green arrow).
    permissiveClearance: Prepare to stop. Vehicle may proceed if unable to stop. Conflicting traffic may be present.
    protectedClearance: Prepare to stop. Vehicle may proceed if unable to stop. 
    cautionConflictingTraffic: Proceed with caution. Conflicting traffic may be present. 
    <Object Identifier> 1.3.6.1.4.1.1206.4.2.1.16.12.1.5
    <Object Type> P"
    REFERENCE "SAE J2735 DE_MovementPhaseState"
    DEFVAL { 2 }
    ::= { agencySignalStateEntry 5 }

--5.16.10   Maximum Enabled Lanes Concurrency Entries
maxEnabledLanesConcurrency OBJECT-TYPE
    SYNTAX Integer32 (1..255) 
    MAX-ACCESS read-only
    STATUS current
    DESCRIPTION "<Definition> This object indicates the maximum rows which shall appear in the spatEnabledLanesConcurrencyTable object.
    <Object Identifier> 1.3.6.1.4.1.1206.4.2.1.16.13
    <Object Type> S"
    ::= { ascSpat 13 }

--5.16.11   SPaT Enabled Lanes Command
spatEnabledLanesCommand2 OBJECT-TYPE
    SYNTAX Integer32 (0..255)
    MAX-ACCESS read-write
    STATUS current
    DESCRIPTION "<Definition> This object establishes the Enabled lanes for the device to be broadcast in a SPAT message. The value is equal to the enabledLaneIndex in the spatEnabledLanesConcurrencyTable. Each octet within the octet string for enabledLaneConcurrency in that row contains the (revocable) lane number(s) that are enabled. The new set of Enabled lanes will be broadcast at the top of the next cycle.

    A value of zero indicates that there are no enabled lanes. A value of 255 indicates that the device shall cancel this command and shall revert back to the Enabled lanes defined in the timebaseAscActionTable timebaseAscActionLane. Otherwise, the Enabled lanes defined is this command shall override the Enabled lanes defined in timebaseAscActionLane.

    If an unsupported / invalid set of Enabled lanes is called, then the spatPortStatus object shall be SET to enabledLanesError(5) for all valid entries in the spatPortTable.
    <Object Identifier> 1.3.6.1.4.1.1206.4.2.1.16.14
    <Object Type> P"
    REFERENCE "SAE J2735 DF_EnabledLaneList"
    ::= { ascSpat 14 }

--5.17  RSU - ASC Support
rsuAsc OBJECT IDENTIFIER
    ::= { asc 17 }

-- This defines a node for objects to support a CV Application Process in a connected vehicle environment.

MapActivationCode ::= OCTET STRING (SIZE(3))

-- The MapActivationCode consists of those parameters required to activate a MAP Plan message in an ASC. It is defined as an OCTET STRING containing the OER-encoding of the following ASN.1 structure.

-- mapActivationCodeStructure ::= SEQUENCE { 
-- mapPlanIndex INTEGER (1..8), 
-- mapPlanCRC OCTET STRING (SIZE (2)) }
-- mapPlanIndex (8 bits) shall indicate the mapPlanIndex requested.
-- mapPlanCRC (16 bits) shall indicate the mapPlanCRC of the requested mapPlanIndex.

--5.18.1    RSU Signal Phase and Timing Functions
rsuAscSpat OBJECT IDENTIFIER ::= { rsuAsc 1 }

-- This defines a node for objects to support signalized intersection applications in a CV Application Process in a connected vehicle environment.

--5.18.1.1  Maximum Number of ASCs Supported
maxRsuAscs OBJECT-TYPE
    SYNTAX Integer32 (1..32)
    UNITS "movement"
    MAX-ACCESS read-only
    STATUS deprecated
    DESCRIPTION "<Definition> This object contains the maximum number of signal controller entries this RSU supports. Each entry represents a signalized intersection whose signal phase and timing information is broadcast by the RSU. This object indicates the maximum rows which shall appear in the mapIntersectionTable object.
    <Object Identifier> 1.3.6.1.4.1.1206.4.2.1.17.1.1
    <Object Type> S"
    ::= { rsuAscSpat 1 }

--5.18.1.2  SPaT ASC Table
rsuAscSpatTable OBJECT-TYPE
    SYNTAX SEQUENCE OF RsuAscSpatEntry 
    MAX-ACCESS not-accessible
    STATUS deprecated
    DESCRIPTION "<Definition>This table contains information describing the signal phase and timing information for a signalized intersection broadcast by the RSU. The number of rows in this table is equal to the maxRsuAscs object.
    <TableType> static
    <Object Identifier> 1.3.6.1.4.1.1206.4.2.1.17.1.2"
    ::= { rsuAscSpat 2 }

rsuAscSpatEntry OBJECT-TYPE
    SYNTAX RsuAscSpatEntry
    MAX-ACCESS not-accessible
    STATUS deprecated
    DESCRIPTION "<Definition> Signal phase and timing information for a signalized intersection broadcast in a SPAT message.
    <Object Identifier> 1.3.6.1.4.1.1206.4.2.1.17.1.2.1"
    INDEX  { rsuAscSpatIndex }
    ::= { rsuAscSpatTable 1 }

RsuAscSpatEntry::= SEQUENCE {
    rsuAscSpatIndex           INTEGER,
    rsuAscSpatId              INTEGER,
    rsuAscSpatMsgCount        INTEGER,
    rsuAscSpatMinuteOfTheYear INTEGER,
    rsuAscSpatMilliseconds    INTEGER,
    rsuAscSpatEnabledLanes    OCTET STRING }

--5.18.1.2.1    SPaT ASC Index
rsuAscSpatIndex OBJECT-TYPE
    SYNTAX Integer32 (1..32)
    UNITS "node"
    MAX-ACCESS not-accessible
    STATUS deprecated
    DESCRIPTION "<Definition> The index number of the signalized intersection objects in this row. This value shall not exceed the maxRsuAscs object value.
    <Object Identifier> 1.3.6.1.4.1.1206.4.2.1.17.1.2.1.1"
    ::= { rsuAscSpatEntry 1 }

--5.18.1.2.2    SPaT ASC Intersection Identifier
rsuAscSpatId OBJECT-TYPE
    SYNTAX Integer32 (0..65535)
    MAX-ACCESS read-write
    STATUS deprecated
    DESCRIPTION "<Definition> To support SAE J2735, the regionally unique identifier of the intersection.
    <Object Identifier> 1.3.6.1.4.1.1206.4.2.1.17.1.2.1.2"
    REFERENCE "SAE J2735 DE_IntersectionID"
    ::= { rsuAscSpatEntry 2 }

--5.18.1.2.3    SPaT ASC Message Count
rsuAscSpatMsgCount OBJECT-TYPE
    SYNTAX Integer32 (0..127)
    MAX-ACCESS read-only
    STATUS deprecated
    DESCRIPTION "<Definition> To support SAE J2735, a sequence number that is incremented when the contents for the intersection in the SPaT data message has changed.
    <Object Identifier> 1.3.6.1.4.1.1206.4.2.1.17.1.2.1.3"
    REFERENCE "SAE J2735 DF_IntersectionState and DE_MsgCount"
    ::= { rsuAscSpatEntry 3 }

--5.18.1.2.4    SPaT ASC Message Time
rsuAscSpatMinuteOfTheYear OBJECT-TYPE
    SYNTAX Integer32 (0..527040)
    MAX-ACCESS read-only
    STATUS deprecated
    DESCRIPTION "<Definition> To support SAE J2735, the minute of the current year SPaT data for this intersection in this row was last broadcast by the CV Roadside Process.
    <Object Identifier> 1.3.6.1.4.1.1206.4.2.1.17.1.2.1.4"
    REFERENCE "SAE J2735 DF_IntersectionState and DE_MinuteOfTheYear"
    DEFVAL { 0 }
    ::= { rsuAscSpatEntry 4 }

--5.18.1.2.5    SPaT ASC Message Time (Milliseconds)
rsuAscSpatMilliseconds OBJECT-TYPE
    SYNTAX Integer32 (0..65535)
    MAX-ACCESS read-only
    STATUS deprecated
    DESCRIPTION "<Definition> To support SAE J2735, the millisecond of the current minute (rsuAscSpatMinuteOfTheYear) SPaT data for this intersection in this row was generated.
    <Object Identifier> 1.3.6.1.4.1.1206.4.2.1.17.1.2.1.5"
    REFERENCE "SAE J2735 DF_IntersectionState and DE_DSecond"
    DEFVAL { 0 }
    ::= { rsuAscSpatEntry 5 }

--5.18.1.2.6    SPaT ASC Message Enabled Lanes
rsuAscSpatEnabledLanes OBJECT-TYPE
    SYNTAX OCTET STRING
    MAX-ACCESS read-write
    STATUS deprecated
    DESCRIPTION "<Definition> To support SAE J2735, this object is used to indicate the Enabled lanes list generated by a specific signal controller and broadcast in a SPaT message. Each octet within the octet string contains the mapLaneIndex(s) (binary value) in the MAP plan data configuration that is broadcast to be ACTIVE. Lanes that may not always be ACTIVE (enabled) are identified as a RevocableLane (Bit 0) in mapLaneType. If a lane is to be identified as ACTIVE, the mapLaneIndex is added to this OCTET STRING.
    <Object Identifier> 1.3.6.1.4.1.1206.4.2.1.17.1.2.1.6"
    REFERENCE "SAE J2735 DF_EnabledLaneList"
    DEFVAL { "" }
    ::= { rsuAscSpatEntry 6 }

--5.18.1.3  SPaT Message Time
rsuSpatMinuteOfTheYear OBJECT-TYPE
    SYNTAX Integer32 (0..527040)
    MAX-ACCESS read-only
    STATUS deprecated
    DESCRIPTION "<Definition> To support SAE J2735, the minute of the current year a SPaT message was last broadcast by the CV Roadside Process.
    <Object Identifier> 1.3.6.1.4.1.1206.4.2.1.17.1.3"
    REFERENCE "SAE J2735 MSG_SignalPhaseAndTiming Message and DE_MinuteOfTheYear"
    DEFVAL { 0 }
    ::= { rsuAscSpat 3 }

--5.17.1.1 Control Active MAP Plan
mapActivatePlan OBJECT-TYPE
    SYNTAX MapActivationCode
    MAX-ACCESS read-write
    STATUS current
    DESCRIPTION "<Definition> A code indicating the active MAP plan. The value of this object may be SET by a management station. If a GET is performed on this object, the device shall respond with the value for the last MAP plan that was successfully activated.

The mapActivatePlanError object shall be updated appropriately upon any attempt to update the value of this object. If a MAP plan activation error occurs (e.g., mapActivatePlanError is updated to a value other than 'none'), the new MAP plan shall not be activated and a genErr shall be returned. A management station should then GET the mapActivatePlanError object as soon as possible to minimize the chance of additional activation attempts from overwriting the mapActivatePlanError.

A value of zero0 00 00 indicates no MAP plan is active and thus no MAP data should be broadcast.
    <Object Identifier> 1.3.6.1.4.1.1206.4.2.1.17.1.4"
    ::= { rsuAscSpat 4 }

-- 5.18.1.5 Active MAP Plan Error
mapActivatePlanError OBJECT-TYPE
    SYNTAX INTEGER { other (1),
                     none (2),
                     mapPlanIndex (3),
                     mapPlanCRC (4) }
    MAX-ACCESS read-only
    STATUS deprecated
    DESCRIPTION "<Definition> This is an error code used to identify why a commanded MAP plan was not not implemented.
other: any error not defined by this standard. 
none: no error.
mapPlanIndex: the MAP plan index requested is not supported or is not defined (populated) by the device.
mapPlanCRC: the checksum in the mapActivatePlan is different than the CRC value contained in the 'mapPlanCRC'.
    <Object Identifier> 1.3.6.1.4.1.1206.4.2.1.17.1.5"
    ::= { rsuAscSpat 5 }

--5.17.2    Connected Detection Zone
ascCvDetector OBJECT IDENTIFIER
    ::= { rsuAsc 2 }

-- This defines a node for a CV Application Process to support detection of connected devices in a connected vehicle environment.

--5.17.2.1  Connected Detection Zone Enable
cvDetectionEnable OBJECT-TYPE
    SYNTAX Integer32 (0..1)
    MAX-ACCESS read-write
    STATUS current
    DESCRIPTION "<Definition> This object is used to enable/disable detection zones in a connected vehicle environment. If enabled, the CU allows detectors defined in vehicleDetectorTable and pedestrianDetectorTable to use inputs from the connected vehicle environment. Inputs may be in the form of actuations, safety messages and/or detection reports in the detectionReportTable.

    TRUE (one) - CV Detection
    FALSE (zero) - No CV Detection 
    <Object Identifier> 1.3.6.1.4.1.1206.4.2.1.17.2.1"
    DEFVAL  { 0 }
    ::= { ascCvDetector 1 }

--5.17.2.2  Maximum Connected Detection Zones 
maxCvDetectionZones OBJECT-TYPE
    SYNTAX Integer32 (1..255)
    MAX-ACCESS read-only
    STATUS current
    DESCRIPTION "<Definition> The maximum number of connected vehicle detection zones this RSU supports. This object indicates the maximum rows which appear in the ascCvDetectorTable object.
    <Object Identifier> 1.3.6.1.4.1.1206.4.2.1.17.2.2"
    ::= { ascCvDetector 2 }

--5.17.2.3  Connected Detection Zone Table
ascCvDetectorTable OBJECT-TYPE
    SYNTAX SEQUENCE OF AscCvDetectorEntry
    MAX-ACCESS not-accessible
    STATUS current
    DESCRIPTION "<Definition> A table containing the connected vehicle detection zone parameters for this RSU. The number of rows in this table is equal to the maxCvDetectionZones object.
    <TableType> static
    <Object Identifier> 1.3.6.1.4.1.1206.4.2.1.17.2.3"
    ::= { ascCvDetector 3 }

ascCvDetectorEntry OBJECT-TYPE
    SYNTAX AscCvDetectorEntry
    MAX-ACCESS not-accessible
    STATUS current
    DESCRIPTION "<Definition> Parameters for a specific connected vehicle detection zone.
    <Object Identifier> 1.3.6.1.4.1.1206.4.2.1.17.2.3.1"
    INDEX { ascCvDetectorNumber }
    ::= { ascCvDetectorTable 1 }

AscCvDetectorEntry ::= SEQUENCE {
    ascCvDetectorNumber         Integer32,
    ascCvDetectorOptions        Integer32, 
    ascCvDetectorIntersection   Integer32, --deprecated
    ascCvDetectorInput          OCTET STRING, --deprecated
    ascCvDetectorAssignment     OCTET STRING, --deprecated 
    ascCvDetectorSamplePeriod   INTEGER, --deprecated
    ascCvDetectorUserClass      INTEGER, --deprecated   
    ascCvDetectorHeading        INTEGER, --deprecated
    ascCvDetectorMinSpeed       INTEGER, --deprecated
    ascCvDetectorMaxSpeed       INTEGER, --deprecated
    ascCvDetectorMinSize        INTEGER, --deprecated
    ascCvDetectorMaxSize        INTEGER, --deprecated
    ascCvDetectorFlags          INTEGER, --deprecated
    ascCvDetectorPort           Integer32,
    ascCvDetectorAssignedInput  Integer32,
    ascCvDetectorAgpDuration    Integer32,
    ascCvDetectorRlvwMinHeading Integer32,
    ascCvDetectorRlvwMaxHeading Integer32,
    ascCvDetectorAgpLatitude    Integer32,
    ascCvDetectorAgpLongitude   Integer32 }

--5.17.2.3.1   Connected Detection Zone Number
ascCvDetectorNumber OBJECT-TYPE
    SYNTAX Integer32 (1..255)
    MAX-ACCESS not-accessible
    STATUS current
    DESCRIPTION "<Definition> The connected vehicle detection zone number for objects in this row. This value shall not exceed the maxCvDetectionZones object value.
    <Object Identifier> 1.3.6.1.4.1.1206.4.2.1.17.2.3.1.1"
    ::= { ascCvDetectorEntry 1 }

--5.17.2.3.2    Connected Detection Zone Options Parameter
ascCvDetectorOptions OBJECT-TYPE
    SYNTAX Integer32 (0..255)
    MAX-ACCESS read-write
    STATUS current
    DESCRIPTION "<Definition> Connected Detection Zone Options Parameter as follows (0=Disabled, 1=Enabled):
    Bit 7: Reserved
    Bit 6: Enable Processed data    - enables the exchange of detectionReports across the ASC - RSU interface.
    Bit 5: Reserved
    Bits 3 & 4: Indicates which detector table the detector number in ascCvDetectorAssignment is assigned to.
    Bit 3 = 0, Bit 4 = 0    - unknown or not applicable
    Bit 3 = 1, Bit 4 = 0    - vehicleDetectorTable
    Bit 3 = 0, Bit 4 = 1    - pedestrianDetectorTable
    Bit 4 = 1, Bit 4 = 1    - Reserved
    Bit 2: Reserved
    Bit 1: A bit value of 1 enables the processing of Personal Safety messages (PSMs) detected within the detection zone.
    Bit 0: A bit value of 1 enables the processing of Basic Safety Messages (BSMs) detected within the detection zone.
    <Object Identifier> 1.3.6.1.4.1.1206.4.2.1.17.2.3.1.2
    <Object Type> P"
    ::= { ascCvDetectorEntry 2 }

--5.18.2.3.3    Connected Detection Intersection
ascCvDetectorIntersection OBJECT-TYPE
    SYNTAX Integer32 (0..65535)
    MAX-ACCESS read-write
    STATUS deprecated
    DESCRIPTION "<Definition> An object referencing the intersection that this connected vehicle detection zone is associated with. This reference is used to establish which controller unit the actuations are intended for and the reference point for the geometric boundaries of the detection zone (ascCvDetectorInput). 0 indicates no intersection has been associated with this CV detection zone.
    <Object Identifier> 1.3.6.1.4.1.1206.4.2.1.17.2.3.1.3"
    DEFVAL { 0 }
    ::= { ascCvDetectorEntry 3 }

--5.18.2.3.4    Connected Detection Zone Input
ascCvDetectorInput OBJECT-TYPE
    SYNTAX OCTET STRING
    MAX-ACCESS read-write
    STATUS deprecated
    DESCRIPTION "<Definition> A null octet string indicates there is no geographic boundary, so any safety message received that satisfies the other criteria defined in the row is valid, regardless of its geographic location.
If Bit 2 of ascCvDetectorOptions is equal to 0, then each octet within the octet string represents a mapLaneIndex that defines the geographic boundaries of the detection zone for this connected device detector. If Bit 2 of ascCvDetectorOptions is equal to 1, then the octet represents the detectionZoneNodePointIndex that defines the geometric boundaries for this connected vehicle detector.
The maximum size of this octet string is equal to the greater of maxLanes or maxDetectionZoneNodePoints.
    <Object Identifier> 1.3.6.1.4.1.1206.4.2.1.17.2.3.1.4"
    DEFVAL { "" }
    ::= { ascCvDetectorEntry 4 }

--5.18.2.3.5    Connected Detection Zone Assignment Parameter
ascCvDetectorAssignment OBJECT-TYPE
    SYNTAX OCTET STRING
    MAX-ACCESS read-write
    STATUS deprecated
    DESCRIPTION "<Definition> Each octet in this octet string represents a detector number in the appropriate detector table (as defined in Bits 3 and 4 in ascCvDetectorOptions) of the reference intersection (ascCvDetectorIntersection) that this connected vehicle detector is assigned to. Any Basic Safety Messages or Personal Safety Messages that satisfy all the criteria defined in the row will result in an actuation for this detector or can be used as an input for this detector. A null value indicates this detection zone is not assigned to any detector number.
    <Object Identifier> 1.3.6.1.4.1.1206.4.2.1.17.2.3.1.5"
    DEFVAL { "" }
    ::= { ascCvDetectorEntry 5 }

--5.18.2.3.6    Connected Detection Zone Sampling Period Parameter
ascCvDetectorSamplePeriod OBJECT-TYPE
    SYNTAX Integer32 (0..255)
    UNITS "second"
    MAX-ACCESS read-write
    STATUS deprecated
    DESCRIPTION "<Definition> This object defines the frequency (in seconds) that a detection report for this connected vehicle detection zone is generated and exchanged. This object is enabled if the collection of processed data is enabled (ascCvDetectionOptions, Bit 7 = 1).
    <Object Identifier> 1.3.6.1.4.1.1206.4.2.1.17.2.3.1.6"
    DEFVAL { 0 }
    ::= { ascCvDetectorEntry 6 }

--5.18.2.3.7    Connected Detection Zone User Class Parameter
ascCvDetectorUserClass OBJECT-TYPE
    SYNTAX Integer32 (0..255)
    MAX-ACCESS read-write
    STATUS deprecated
    DESCRIPTION "<Definition> The mapUserClassId value to which this connected vehicle detection zone applies to. Only connected devices that satisfy all of the vehicle types defined may result in an actuation for this detector. A value of zero indicates that any vehicle type may result in an actuation.
    <Object Identifier> 1.3.6.1.4.1.1206.4.2.1.17.2.3.1.7"
    ::= { ascCvDetectorEntry 7 }

--5.18.2.3.8    Connected Detection Zone Heading Parameter
ascCvDetectorHeading OBJECT-TYPE
    SYNTAX Integer32 (0..65535)
    MAX-ACCESS read-write
    STATUS deprecated
    DESCRIPTION "<Definition> To support SAE J2735, this object represents heading slices that this connected vehicle detection zone applies to. Only connected devices that have a current heading within one of the enabled heading slices may result in an actuation for this detector. A value of 1 indicates that the heading slice is enabled.
    <Object Identifier> 1.3.6.1.4.1.1206.4.2.1.17.2.3.1.8"
    REFERENCE "SAE J2735 DE_HeadingSlice"
    DEFVAL { 0 }
    ::= { ascCvDetectorEntry 8 }

--5.18.2.3.9    Connected Detection Zone Minimum Speed Parameter
ascCvDetectorMinSpeed OBJECT-TYPE
    SYNTAX Integer32 (0..8191)
    MAX-ACCESS read-write
    STATUS deprecated
    DESCRIPTION "<Definition> This object represents the minimum speed, in 0.02 meters per second units, that this connected vehicle detection zone applies to. A value of zero indicates that the connected vehicle detection zone applies to connected devices of any speed. A value of 8190 indicates the detector zone applies only to speeds equal to or greater than 40.90 meters per second.
    <Object Identifier> 1.3.6.1.4.1.1206.4.2.1.17.2.3.1.9"
    DEFVAL { 0 }
    ::= { ascCvDetectorEntry 9 }

--5.18.2.3.10   Connected Detection Zone Maximum Speed Parameter
ascCvDetectorMaxSpeed OBJECT-TYPE
    SYNTAX Integer32 (0..8191)
    UNITS "0.02 meters per second"
    MAX-ACCESS read-write
    STATUS deprecated
    DESCRIPTION "<Definition> This object represents the maximum speed, in 0.02 meters per second units, that this connected vehicle detection zone applies to. A value of zero is reserved. A value of 8190 indicates that the connected vehicle detection zone applies to connected devices that are equal to or less than 40.90 meters per second. A value of 8191 indicates that this object is not used and that the connected vehicle detection zone applies to connected devices of any speed.
    <Object Identifier> 1.3.6.1.4.1.1206.4.2.1.17.2.3.1.10"
    DEFVAL { 8191 }
    ::= { ascCvDetectorEntry 10 }

--5.18.2.3.11   Connected Detection Zone Minimum Vehicle Size Parameter
ascCvDetectorMinSize OBJECT-TYPE
    SYNTAX Integer32 (0..4194303)
    MAX-ACCESS read-write
    STATUS deprecated
    DESCRIPTION "<Definition> This object represents the minimum vehicle size, in centimeters, that this connected vehicle detection zone applies to. Bits 0 to 9 represents the minimum width of the vehicle, and Bits 10 to 21 represents the minimum length of the vehicle. A value of zero indicates that the connected vehicle detection zone applies to connected devices of any size. This object is valid only for BSMs.
    <Object Identifier> 1.3.6.1.4.1.1206.4.2.1.17.2.3.1.11"
    DEFVAL { 0 }
    ::= { ascCvDetectorEntry 11 }

--5.18.2.3.12   Connected Detection Zone Maximum Vehicle Size Parameter
ascCvDetectorMaxSize OBJECT-TYPE
    SYNTAX Integer32 (0..4194303)
    UNITS "0.02 meters per second"
    MAX-ACCESS read-write
    STATUS deprecated
    DESCRIPTION "<Definition> This object represents the maximum vehicle size, in centimeters, that this connected vehicle detection zone applies to. Bits 0 to 9 represents the maximum width of the vehicle, and Bits 10 to 21 represents the maximum length of the vehicle. A value of zero is reserved. A value of 4194303 indicates that this object is not used and that the connected vehicle detection zone applies to connected devices of any s.ize.
    <Object Identifier> 1.3.6.1.4.1.1206.4.2.1.17.2.3.1.12"
    DEFVAL { 4194303 }
    ::= { ascCvDetectorEntry 12 }

--5.18.2.3.13   Connected Detection Zone Flags Parameter
ascCvDetectorFlags OBJECT-TYPE
    SYNTAX INTEGER(0..255)
    MAX-ACCESS read-write
    STATUS deprecated
    DESCRIPTION "<Definition> To support SAE J2735, this object represents a filter for the event flags and brake status of a connected vehicle that this connected vehicle detection zone applies to. If a value is set to true (set to 1), this indicates that only basic safety messages whose event flag status is also true will result in an actuation, will be exchanged, or will be stored (as appropriate) for that connected device detection zone. If multiple values are set to true, then any basic safety messages that satisfy ANY ONE of those values will result in an actuation, exchanged, or stored (i.e., this is an OR object).
    Bit 15:     braking active
    Bit 14:     brake boost assist engaged
    Bit 13:     auxiliary brake engaged
    Bit 12: Air bags deployed
    Bit 11: Vehicle disabled
    Bit 10: Flat tire
    Bit 9:  Status of wiper (front or back) changed within last the 2 seconds
    Bit 8:  Status of the exterior lights changed within the last 2 seconds
    Bit 7:  Hard braking (greater than 0.4 g)
    Bit 6:  Reserved
    Bit 5:  Carrying hazardous materials and placarded as such
    Bit 4:  Stability control active and exceeding 100 mSec
    Bit 3:  Traction control active and exceeding 100 mSec
    Bit 2:  Anti Lock Brakes active and exceeding 100 mSec
    Bit 1:  Stop line violation
    Bit 0:  Hazard lights are active
    <Object Identifier> 1.3.6.1.4.1.1206.4.2.1.17.2.3.1.13"
    REFERENCE "SAE J2735 DF_BrakeSystemStatus DE_VehicleEventFlags"
    DEFVAL { 0 }
    ::= { ascCvDetectorEntry 13 }

-- 5.17.2.3.3   Connected Detection Zone Port
ascCvDetectorPort OBJECT-TYPE
    SYNTAX Integer32 (0..255)
    MAX-ACCESS read-write
    STATUS current
    DESCRIPTION "<Definition> This object defines the ifIndex for a row in the ifTable and the commPortTable that identifies a communications port on the ASC that is used to receive connected vehicle messages for placing actuations on detector defined in ascCvDetectorAssignedInput.
    A value of zero means no port is associated with this connected vehicle detector. 
    <Object Identifier> 1.3.6.1.4.1.1206.4.2.1.17.2.3.1.14
    <Object Type> P"
    ::= {  ascCvDetectorEntry 14 }

-- 5.17.2.3.4   Connected Detection Zone Assigned Input
ascCvDetectorAssignedInput OBJECT-TYPE
    SYNTAX Integer32 (1..255)
    MAX-ACCESS read-write
    STATUS current
    DESCRIPTION "<Definition> This object defines a vehicle detector or pedestrian detector that is actuated when an actuation is placed on this CV Detector. An actuation on the assigned detector will call the assigned detectors call phase. The diagnostic parameters of the assigned detector will also apply to this CV Detector. Whether this is a vehicle detector or pedestrian detector is defined in ascCvDetectorOptions. This value shall not exceed maxVehicleDetectors or maxPedestrianDetectors as configured. 
    <Object Identifier> 1.3.6.1.4.1.1206.4.2.1.17.2.3.1.15
    <Object Type> P"
    ::= {  ascCvDetectorEntry 15 }

-- 5.17.2.3.5   Connected Detection Zone AGP Duration
ascCvDetectorAgpDuration OBJECT-TYPE
    SYNTAX Integer32 (0..255)
    UNITS "decisecond"
    MAX-ACCESS read-write
    STATUS current
    DESCRIPTION "<Definition> This object defines a FIXED duration of the Assured Green Period, in tenth seconds. If a connected vehicle is detected at the location defined by ascCvDetectorAgpLatitude and ascCvDetectorAgpLongitude while the assigned phase of the detector in ascCvDetectorAssignedInput is GREEN, the assigned phase is extended by as much as this duration. A phase may not be extended beyond its programmed maximum green time. A value of zero means Assured Green Period is not used. 
    <Object Identifier> 1.3.6.1.4.1.1206.4.2.1.17.2.3.1.16
    <Object Type> P"
    ::= {  ascCvDetectorEntry 16 }

-- 5.17.2.3.6   Connected Detection Zone RLVW Minimum Heading
ascCvDetectorRlvwMinHeading OBJECT-TYPE
    SYNTAX Integer32 (0..28800)
    UNITS "0.0125 degree"
    MAX-ACCESS read-write
    STATUS current
    DESCRIPTION "<Definition> This object defines the lower threshold for a vehicle heading for the Assured Green Period defined in ascCvDetectorAgpDuration to be applied to the assigned phase of the detector defined in ascCvDetectorAssignedInput. A value of zero indicates that this heading is not used for applying Assured Green Period.
    <Object Identifier> 1.3.6.1.4.1.1206.4.2.1.17.2.3.1.17
    <Object Type> P"
    REFERENCE "SAE J2735 DE_Heading"
    ::= {  ascCvDetectorEntry 17 }

-- 5.17.2.3.7  Connected Detection Zone RLVW Maximum Heading
ascCvDetectorRlvwMaxHeading OBJECT-TYPE
    SYNTAX Integer32 (0..28800)
    UNITS "0.0125 degree"
    MAX-ACCESS read-write
    STATUS current
    DESCRIPTION "<Definition> This object defines the upper threshold for a vehicle heading for a the Assurred Green Period defined in ascCvDetectorAgpDuration to be applied to the assigned phase of the detector defined in ascCvDetectorAssignedInput. A value of zero indicates that this heading is not used for applying Assured Green Period.
    <Object Identifier> 1.3.6.1.4.1.1206.4.2.1.17.2.3.1.18
    <Object Type> P"
    REFERENCE "SAE J2735 DE_Heading"
    ::= {  ascCvDetectorEntry 18 }

-- 5.17.2.3.8   Connected Detection Zone AGP Application Latitude
ascCvDetectorAgpLatitude  OBJECT-TYPE
    SYNTAX Integer32 (-90000000..90000001)
    UNITS "1/10 microdegree"
    MAX-ACCESS read-write
    STATUS current
    DESCRIPTION "<Definition> This object defines the latitude of the reference point long the upstream edge of stopping distance used to compute the time when the Assured Green Period is to be applied. This value is ignored if ascCvDetectorAgpDuration is zero.
    <Object Identifier> 1.3.6.1.4.1.1206.4.2.1.17.2.3.1.19
    <Object Type> P"
    REFERENCE "SAE J2735 DE_Latitude"
    ::= {  ascCvDetectorEntry 19 }

-- 5.17.2.3.9   Connected Detection Zone AGP Application Longitude
ascCvDetectorAgpLongitude OBJECT-TYPE
    SYNTAX Integer32 (-179999999..180000001)
    UNITS "1/10 microdegree"
    MAX-ACCESS read-write
    STATUS current
    DESCRIPTION "<Definition> This object defines the longitude of the reference point long the upstream edge of stopping distance used to compute the time when the Assured Green Period is to be applied. This value is ignored if ascCvDetectorAgpDuration is zero.
    <Object Identifier> 1.3.6.1.4.1.1206.4.2.1.17.2.3.1.20
    <Object Type> P"
    REFERENCE "SAE J2735 DE_Latitude"
    ::= {  ascCvDetectorEntry 20 }

--5.18.2.4  Maximum Connected Detection Zone Node Points
maxDetectionZoneNodePoints OBJECT-TYPE
    SYNTAX INTEGER(2..255)
    MAX-ACCESS read-only
    STATUS deprecated
    DESCRIPTION "<Definition> The maximum number of connected vehicle detection zone node points this CU supports. This object indicates the maximum rows which appear in the detectionZoneNodePointTable object.
    <Object Identifier> 1.3.6.1.4.1.1206.4.2.1.17.2.4"
    DEFVAL  { 63 }
    ::= { ascCvDetector 4 }

--5.18.2.5  Connected Detection Zone Table
detectionZoneNodePointTable OBJECT-TYPE
    SYNTAX SEQUENCE OF DetectionZoneNodePointEntry
    MAX-ACCESS not-accessible
    STATUS deprecated
    DESCRIPTION "<Definition> A table containing the node points for a connected vehicle detection zone parameters in this RSU. The number of rows in this table is equal to the maxDetectionZoneNodePoints object.
    <TableType> static
    <Object Identifier> 1.3.6.1.4.1.1206.4.2.1.17.2.5"
    ::= { ascCvDetector 5 }

detectionZoneNodePointEntry OBJECT-TYPE
    SYNTAX DetectionZoneNodePointEntry
    MAX-ACCESS not-accessible
    STATUS deprecated
    DESCRIPTION "<Definition> Location of node points for a specific connected vehicle detection zone.
    <Object Identifier> 1.3.6.1.4.1.1206.4.2.1.17.2.5.1"
    INDEX { detectionZoneNodePointIndex }
    ::= { detectionZoneNodePointTable 1 }

DetectionZoneNodePointEntry ::= SEQUENCE {
    detectionZoneNodePointIndex  INTEGER,--deprecated
    detectionZoneNodePointX      INTEGER,--deprecated
    detectionZoneNodePointY      INTEGER,--deprecated
    detectionZoneNodePointWidth  INTEGER,--deprecated
    detectionZoneNodePointZ      INTEGER,--deprecated
    detectionZoneNodePointHeight INTEGER }--deprecated

--5.18.2.5.1    Connected Detection Zone Node Point Index
detectionZoneNodePointIndex OBJECT-TYPE
    SYNTAX INTEGER(1..255)
    MAX-ACCESS not-accessible
    STATUS deprecated
    DESCRIPTION "<Definition> An index for the detection zone node points for objects in this row. This value shall not exceed the maxDetectionZoneNodePoints object value.
    <Object Identifier> 1.3.6.1.4.1.1206.4.2.1.17.2.5.1.1"
    ::= { detectionZoneNodePointEntry 1 }

--5.18.2.5.2    Detection Zone Node Point X
detectionZoneNodePointX OBJECT-TYPE
    SYNTAX INTEGER (-32767..32767)
    UNITS "centimeter"
    MAX-ACCESS read-write 
    STATUS deprecated 
    DESCRIPTION "<Definition>Represents the X offset, in centimeters, from the previous node point (defined in the previous row of this table, with the first path node defined in the row detectionZoneNodePointIndex = 1). For row detectionZoneNodePointIndex = 1, the offset is from the reference point of the referenced intersection (ascCvDetectorIntersection). The sequence of nodes defines the centerline of the detection zone. A positive value is to the East.
    <Object Identifier> 1.3.6.1.4.1.1206.4.2.1.17.2.5.1.2"
    ::= { detectionZoneNodePointEntry 2 }

--5.18.2.5.3    Detection Zone Node Point Y
detectionZoneNodePointY OBJECT-TYPE
    SYNTAX INTEGER (-32767..32767)
    UNITS "centimeter"
    MAX-ACCESS read-write 
    STATUS deprecated
    DESCRIPTION "<Definition>Represents the Y offset, in centimeters, from the previous node point (defined in the previous row of this table, with the first node point defined in the row detectionZoneNodePointIndex = 1). For detectionZoneNodePointIndex = 1, the offset is from the reference point of the referenced intersection (ascCvDetectorIntersection). The sequence of node points defines the centerline of the zone. A positive value is to the North.
    <Object Identifier> 1.3.6.1.4.1.1206.4.2.1.17.2.5.1.3"
    ::= { detectionZoneNodePointEntry 3 }

--5.18.2.5.4    Detection Zone Node Point Width
detectionZoneNodePointWidth OBJECT-TYPE
    SYNTAX INTEGER (-32767..32767)
    UNITS "centimeter"
    MAX-ACCESS read-write 
    STATUS deprecated
    DESCRIPTION "<Definition> A value added to the current zone width at this node and from this node onwards, in 1 centimeter steps. Lane widths between nodes are a linear taper between points.
    <Object Identifier> 1.3.6.1.4.1.1206.4.2.1.17.2.5.1.4"
    ::= { detectionZoneNodePointEntry 4 }

--5.18.2.5.5    Detection Zone Node Point Z
detectionZoneNodePointZ OBJECT-TYPE
    SYNTAX INTEGER (-32767..32767)
    UNITS "centimeter"
    MAX-ACCESS read-write 
    STATUS deprecated 
    DESCRIPTION "<Definition>Represents the Z offset, in centimeters, from the previous node point (defined in the previous row of this table, with the first node point defined in the row detectionZoneNodePointIndex = 1). For detectionZoneNodePointIndex = 1, the offset is from the reference point of the referenced intersection (ascCvDetectorIntersection). The sequence of node points defines the elevation of the roadway pavement that the zone is on top of. A positive value represents a higher elevation.
    <Object Identifier> 1.3.6.1.4.1.1206.4.2.1.17.2.5.1.5
"
    ::= { detectionZoneNodePointEntry 5 }

--5.18.2.5.6    Detection Zone Node Point Height
detectionZoneNodePointHeight OBJECT-TYPE
    SYNTAX Integer32 (0..32767)
    UNITS "centimeter"
    MAX-ACCESS read-write 
    STATUS deprecated
    DESCRIPTION "<Definition> The height, in centimeters, above the roadway pavement for the detection zone. This value is added to the detectionZoneNodePointZ to represent the upper boundary of the detection zone. The detection zone height between node points are a linear taper between points.
    <Object Identifier> 1.3.6.1.4.1.1206.4.2.1.17.2.5.1.6"
    ::= { detectionZoneNodePointEntry 6 }

--5.18.2.6  Detection Actuations Sample Period
cvDetectionActuationSamplePeriod OBJECT-TYPE
    SYNTAX Integer32 (0..65535)
    UNITS "millisecond"
    MAX-ACCESS read-write
    STATUS deprecated
    DESCRIPTION "The sample period for updating the cvDetectionActuations object, in units of milliseconds. If the value is zero (0), then the cvDetectionActuations is not collected on a periodic basis.
    <Object Identifier> 1.3.6.1.4.1.1206.4.2.1.17.2.6"
    DEFVAL { 0 }
    ::= { ascCvDetector 6 }

--5.18.2.7  Maximum Connected Detection Zone Groups
maxCvDetectionGroups OBJECT-TYPE
    SYNTAX Integer32 (1..32)
    UNITS "centimeter"
    MAX-ACCESS read-only 
    STATUS deprecated 
    DESCRIPTION "<Definition> The maximum number of connected vehicle detection zone groups (8 connected detection zones per group) this RSU supports. This value is equal to TRUNCATE [(maxCvDetectionZones + 7) / 8]. This object indicates the maximum rows which shall appear in the cvDetectionGroupTable.
    <Object Identifier> 1.3.6.1.4.1.1206.4.2.1.17.2.7
    <Object Type> S"
    ::= { ascCvDetector 7 }

--5.18.2.8  Detection Group Table
cvDetectionGroupTable OBJECT-TYPE
    SYNTAX SEQUENCE OF CvDetectionGroupEntry
    MAX-ACCESS not-accessible
    STATUS deprecated
    DESCRIPTION "<Definition> A table containing status information in groups of eight connected vehicle detection zones (ascCvDetectorNumber). The number of rows in this table is equal to the maxCvDetectionGroups object.
    <Object Identifier> 1.3.6.1.4.1.1206.4.2.1.17.2.8"
    ::= { ascCvDetector 8 }

cvDetectionGroupEntry OBJECT-TYPE
    SYNTAX CvDetectionGroupEntry
    MAX-ACCESS not-accessible
    STATUS deprecated
    DESCRIPTION "<Definition> The status for eight connected vehicle device detectors.
    <Object Identifier> 1.3.6.1.4.1.1206.4.2.1.17.2.8.1"
    INDEX { cvDetectionGroupNumber }
    ::= { cvDetectionGroupTable 1 }

CvDetectionGroupEntry  ::= SEQUENCE {
    cvDetectionGroupNumber     Integer32,
    cvDetectionGroupActuations Integer32 }

--5.18.2.8.1    CV Detection Group Number
cvDetectionGroupNumber OBJECT-TYPE
    SYNTAX Integer32 (1..32)
    UNITS "group"
    MAX-ACCESS not-accessible
    STATUS deprecated
    DESCRIPTION "<Definition> The CV Detection Group number for objects in this row. This value shall not exceed the maxCvDetectionGroups object value.
    <Object Identifier> 1.3.6.1.4.1.1206.4.2.1.17.2.8.1.1
    <Object Type> S"
    ::= { cvDetectionGroupEntry 1 }

--5.18.2.8.2    CV Detection Group Actuations
cvDetectionGroupActuations OBJECT-TYPE
    SYNTAX Integer32 (0..255)
    MAX-ACCESS read-only
    STATUS deprecated
    DESCRIPTION "<Definition> CV Detection Actuation Mask, where when a bit = 1, the CV Detection is currently actuated. When a bit = 0, the CV Detection is NOT currently actuated.
    Bit 7: CV Detection # = (cvDetectionGroupNumber * 8)
    Bit 6: CV Detection # = (cvDetectionGroupNumber * 8) - 1
    Bit 5: CV Detection # = (cvDetectionGroupNumber * 8) - 2
    Bit 4: CV Detection # = (cvDetectionGroupNumber * 8) - 3
    Bit 3: CV Detection # = (cvDetectionGroupNumber * 8) - 4
    Bit 2: CV Detection # = (cvDetectionGroupNumber * 8) - 5
    Bit 1: CV Detection # = (cvDetectionGroupNumber * 8) - 6
    Bit 0: CV Detection # = (cvDetectionGroupNumber * 8) - 7
    <Object Identifier> 1.3.6.1.4.1.1206.4.2.1.17.2.8.1.2
    <Object Type> S"
    ::= { cvDetectionGroupEntry 2 }

--5.18.2.9  CV Detection Report Collection
detectionReportCollection OBJECT-TYPE
    SYNTAX Integer32 (0..255)
    MAX-ACCESS read-write
    STATUS deprecated
    DESCRIPTION "<Definition> This object determines what pieces of data will be exchanged and stored for the detectionReportTable. A value set to 1 indicates that piece of data shall be stored.
    Bit 6 & 7 = Reserved
    Bit 5 = platoon     - detectionReportPlatoon
    Bit 4 = gap         - detectionReportGap
    Bit 3 = queue length    - detectionReportQueue
    Bit 2 = travel time - detectionReportTravelTime
    Bit 1 = average speed   - detectionReportSpeed
    Bit 0 = volume      - detectionReportVolume
    <Object Identifier> 1.3.6.1.4.1.1206.4.2.1.17.2.9"
    ::= { ascCvDetector 9 }

--5.17.2.4 Active CV Detectors
activeCvDetectors OBJECT-TYPE
    SYNTAX Integer32 (0..255)
    MAX-ACCESS read-only
    STATUS current
    DESCRIPTION "<Definition> The number of active CV detectors in this device. This object indicates how many rows are in the detectionReportTable object. There shall be a row for every active CV detector collecting CV data.
    <Object Identifier> 1.3.6.1.4.1.1206.4.2.1.17.2.10
    <Object Type> S"
    ::= { ascCvDetector 10 }

--5.17.2.5 Detection Reports Sequence
detectionReportSequence OBJECT-TYPE
    SYNTAX Integer32 (0..65535)
    UNITS "sequence"
    MAX-ACCESS read-only
    STATUS current
    DESCRIPTION "<Definition> This object defines a sequence number for detection reports received from defined connected vehicle detection zones. This object is used to track where a new detection report received by the CU should be stored. The value cycles within the limits of 0 to 65535 and is incremented by one when a detection report is stored in the detectionReportTable.
    <Object Identifier> 1.3.6.1.4.1.1206.4.2.1.17.2.11
    <Object Type> S"
    ::= { ascCvDetector 11 }

--5.17.2.6 Connected Detection Reports Table
detectionReportTable OBJECT-TYPE
    SYNTAX SEQUENCE OF DetectionReportEntry
    MAX-ACCESS not-accessible
    STATUS current
    DESCRIPTION "<Definition> A table containing detector reports for a connected vehicle detection zone defined for this CU. The number of rows in this table is equal to the activeCvDetectors object.
    Note: The objects in this table are read-write to allow the RSU to be the SNMP manager and the ASC to be the SNMP agent across the RSU - ASC interface. 
    <TableType> static
    <Object Identifier> 1.3.6.1.4.1.1206.4.2.1.17.2.12"
    ::= { ascCvDetector 12 }

detectionReportEntry OBJECT-TYPE
    SYNTAX DetectionReportEntry
    MAX-ACCESS not-accessible
    STATUS current
    DESCRIPTION "<Definition> Detection reports received for a specific connected vehicle detection zone.
    <Object Identifier> 1.3.6.1.4.1.1206.4.2.1.17.2.12.1"
    INDEX { ascCvDetectorNumber }
    ::= { detectionReportTable 1 }

DetectionReportEntry ::= SEQUENCE {
    detectionReportTime       Integer32,
    detectionReportVolume     Integer32,
    detectionReportSpeed      Integer32,
    detectionReportTravelTime Integer32,
    detectionReportQueue      Integer32,
    detectionReportGap        Integer32,
    detectionReportPlatoon    Integer32 }

--5.17.2.6.1   Connected Detection Zone Report Time
detectionReportTime OBJECT-TYPE
    SYNTAX Integer32 (0..3601000)
    UNITS "millisecond"
    MAX-ACCESS read-write
    STATUS current
    DESCRIPTION "<Definition> This object indicates the seconds within the hour the detector report is generated.
<Valid Value Rule> 0 to 3600999 are in milliseconds, with a leap second represented by 3600000 to 3600999. A value of 3601000 shall represent unavailable.
    <Object Identifier> 1.3.6.1.4.1.1206.4.2.1.17.2.12.1.1
    <Object Type> P"
    DEFVAL  { 3601000 }
    ::= { detectionReportEntry 1 }

--5.17.2.6.2   Connected Detection Zone Volume Data
detectionReportVolume OBJECT-TYPE
    SYNTAX Integer32 (0..255)
    UNITS "volume"
    MAX-ACCESS read-write
    STATUS current
    DESCRIPTION "<Definition> A count of the number of connected devices currently detected in the connected vehicle detection zone at the time the report was generated. This value shall range from 0 to 254. The value 255 shall indicate volume overflow.
    <Object Identifier> 1.3.6.1.4.1.1206.4.2.1.17.2.12.1.2
    <Object Type> P"
    DEFVAL { 0 }
    ::= { detectionReportEntry 2 }

--5.17.2.6.3   Connected Detection Zone Speed Data
detectionReportSpeed OBJECT-TYPE
    SYNTAX Integer32 (0..255)
    UNITS "0.5 kilometers/hour"
    MAX-ACCESS read-write
    STATUS current
    DESCRIPTION "<Definition> The average speed, in 0.5 kilometers per hour, of the connected devices currently detected in the connected vehicle detection zone at the time the report was generated.
<Valid Value Rule> A value of zero to 253 is the average connected device speed in 0.5 kilometers per hour units. A value of 254 represents an average speed of 127 kilometers per hour or higher. A value of 255 represents an invalid or missing value.
    <Object Identifier> 1.3.6.1.4.1.1206.4.2.1.17.2.12.1.3
    <Object Type> P"
    DEFVAL  { 255 }
    ::= { detectionReportEntry 3 }

--5.17.2.6.4   Connected Detection Zone Travel Time Data
detectionReportTravelTime OBJECT-TYPE
    SYNTAX Integer32 (0..65535)
    UNITS "decisecond"
    MAX-ACCESS read-write
    STATUS current
    DESCRIPTION "<Definition> The average travel time, in tenths of a second, for a connected device to traverse the connected vehicle detection zone at the time the report was generated. A value of 65535 represents an invalid or missing value.
    <Object Identifier> 1.3.6.1.4.1.1206.4.2.1.17.2.12.1.4
    <Object Type> P"
    DEFVAL { 65535 }
    ::= { detectionReportEntry 4 }

--5.17.2.6.5   Connected Detection Zone Queue Data
detectionReportQueue OBJECT-TYPE
    SYNTAX Integer32 (0..255)
    MAX-ACCESS read-write
    STATUS current
    DESCRIPTION "<Definition> A count of the number of connected vehicles currently queued in the connected vehicle detection zone at the time the report was generated.
<ValidValueRule> A value of zero to 253 represents the number of vehicles queued. A value of 254 indicates the queue is 254 or more vehicles. A value of 255 represents an invalid or missing value.
    <Object Identifier> 1.3.6.1.4.1.1206.4.2.1.17.2.12.1.5
    <Object Type> P"
    DEFVAL { 255 }
    ::= { detectionReportEntry 5 }

--5.17.2.6.6   Connected Detection Zone Gap Data
detectionReportGap OBJECT-TYPE
    SYNTAX Integer32 (0..65535)
    UNITS "centimeter"
    MAX-ACCESS read-write
    STATUS current
    DESCRIPTION "<Definition> The average gap, in centimeters, between the connected vehicles currently detected in the connected vehicle detection zone at the time the report was generated. The gap is defined as the distance between the edge of the rear bumper of a connected vehicle and the edge of the front bumper of a connected vehicle behind it. A value of 65535 indicates an invalid or missing value.
    <Object Identifier> 1.3.6.1.4.1.1206.4.2.1.17.2.12.1.6
    <Object Type> P"
    DEFVAL { 65535 }
    ::= { detectionReportEntry 6 }

--5.17.2.6.7   Connected Detection Zone Platoon Data
detectionReportPlatoon OBJECT-TYPE
    SYNTAX Integer32 (0..255)
    UNITS "vehicle"
    MAX-ACCESS read-write
    STATUS current
    DESCRIPTION "<Definition> A count of the number of connected vehicles in a platoon currently detected in the connected vehicle detection zone at the time the report was generated.
<ValidValueRule> A value of zero to 253 represents the number of vehicles in the platoon. A value of 254 indicates the platoon is 254 or more vehicles. A value of 255 represents an invalid or missing value.
    <Object Identifier> 1.3.6.1.4.1.1206.4.2.1.17.2.12.1.7
    <Object Type> P"
    DEFVAL { 255 }
    ::= { detectionReportEntry 7 }

--5.18 ASC - ECLA Interface
ecla OBJECT IDENTIFIER
    ::= { asc 18 }

--5.18.1 ECLA Communications Parameter
eclaCommEnable OBJECT-TYPE 
    SYNTAX Integer32 (0..1)
    MAX-ACCESS read-write
    STATUS current
    DESCRIPTION "<Definition> This object controls if an ASC should use any data received from an ECLA to determine when the current phases may terminate and what phases may be next. 
            TRUE (one) - Use data provided by an ECLA.
            FALSE (zero) - Do not use data provided by an ECLA.

    <Object Identifier> 1.3.6.1.4.1.1206.4.2.18.1
    <Object Type> P"
    DEFVAL { 0 }
    ::= { ecla 1 }

--5.18.2 ECLA Timestamp Input
eclaDataTimestamp OBJECT-TYPE
    SYNTAX Integer32 (0..36111)
    UNITS "decisecond"
    MAX-ACCESS read-write
    STATUS current
    DESCRIPTION "<Definition> The most recent time point when the ECLA provided input into the controller. 

    Values from 0 to 35999 cover one hour. Values from 36000 to 36009 are used when a leap second occurs. Values from 36010 to 36110 are reserved for future use. A value of 36111 indicates the time point of the event is undefined or unknown.

    The device shall reset this object to ZERO when in BACKUP Mode. A write to this object shall reset the Backup timer to ZERO (see unitBackupTime).

    See Annex F.3.3.6.2 for additional guidance.
    <Object Identifier> 1.3.6.1.4.1.1206.4.2.18.2
    <Object Type> C"
    REFERENCE "SAE J2735 DE_TimeMark"
    DEFVAL { 36111 }
    ::= { ecla 2 }

--5.19.3 ECLA Input Table
eclaInputTable OBJECT-TYPE
    SYNTAX SEQUENCE OF EclaEntry
    MAX-ACCESS not-accessible
    STATUS current
    DESCRIPTION "<Definition> A table containing Controller Unit phase
        parameters. The number of rows in this table is equal to the
        maxRings object value.
    <TableType> static
    <Object Identifier> 1.3.6.1.4.1.1206.4.2.18.3"
    ::= { ecla 3 }

eclaEntry OBJECT-TYPE
    SYNTAX EclaEntry
    MAX-ACCESS not-accessible
    STATUS current
    DESCRIPTION "<Definition> Parameters for a specific Controller Unit phase.
    <Object Identifier> 1.3.6.1.4.1.1206.4.2.18.3.1"
    INDEX { sequenceRingNumber }
    ::= { eclaInputTable 1 }

EclaEntry  ::= SEQUENCE { 
    eclaRingCurrentPhase        Integer32,
    eclaRingGreenMinEndTime     Integer32,
    eclaRingGreenMaxEndTime     Integer32,
    eclaRingGreenLikelyEndTime  Integer32,
    eclaRingEndTimeConfidence   Integer32,
    eclaRingNextPhase           Integer32 }


--5.18.3.1 ECLA Ring Current Phase
eclaRingCurrentPhase OBJECT-TYPE
    SYNTAX Integer32 (0..255)
    MAX-ACCESS read-write
    STATUS current
    DESCRIPTION "<Definition> The phase number for the phase currently on for this ring as provided by an ECLA. This is the phase that eclaRingGreenMinEndTime, eclaRingGreenMaxEndTime, eclaRingGreenLikelyEndTime, and eclaRingEndTimeConfidence object values correspond to. 
    
    This value shall not exceed value of maxPhases. A value of zero indicates that the ECLA is currently unable to provide the information. 

    <Object Identifier> 1.3.6.1.4.1.1206.4.2.18.3.1.1
    <Object Type> C"
    DEFVAL { 0 }
    ::= { eclaEntry 1 }

--5.18.3.2 ECLA Ring Current Phase Minimum Green End Time
eclaRingGreenMinEndTime OBJECT-TYPE
    SYNTAX Integer32 (0..36111)
    UNITS "decisecond"
    MAX-ACCESS read-write
    STATUS current
    DESCRIPTION "<Definition> The earliest future time point when the phases in eclaCurrentDataPhase are expected to terminate, as provided by an ECLA. 
    
    Values from 0 to 35999 cover one hour. Values from 36000 to 36009 are used when a leap second occurs. Values from 36010 to 36110 are reserved for future use. A value of 36111 indicates the time point of the event is undefined or unknown.

    See Annex F.3.3.6.3 for additional guidance.
    <Object Identifier> 1.3.6.1.4.1.1206.4.2.18.3.1.2
    <Object Type> C"
    REFERENCE "SAE J2735 DE_TimeMark"
    DEFVAL { 36111 }
    ::= { eclaEntry 2 }

--5.18.3.3 ECLA Ring Current Phase Maximum Green End Time
eclaRingGreenMaxEndTime OBJECT-TYPE
    SYNTAX Integer32 (0..36111)
    UNITS "decisecond"
    MAX-ACCESS read-write
    STATUS current
    DESCRIPTION "<Definition> The latest future time point when the phases in eclaCurrentDataPhase are expected to terminate, as provided by an ECLA. 
    
    Values from 0 to 35999 cover one hour. Values from 36000 to 36009 are used when a leap second occurs. Values from 36010 to 36110 are reserved for future use. A value of 36111 indicates the time point of the event is undefined or unknown.

    See Annex F.3.3.6.3 for additional guidance.
    <Object Identifier> 1.3.6.1.4.1.1206.4.2.18.3.1.3
    <Object Type> C"
    REFERENCE "SAE J2735 DE_TimeMark"
    DEFVAL { 36111 }
    ::= { eclaEntry 3 }

--5.18.3.4 ECLA Ring Current Phase Likely Green End Time
eclaRingGreenLikelyEndTime OBJECT-TYPE
    SYNTAX Integer32 (0..36111)
    UNITS "decisecond"
    MAX-ACCESS read-write
    STATUS current
    DESCRIPTION "<Definition> The most likely future time point when the phases in eclaCurrentDataPhase are expected to terminate, as provided by an ECLA. 

    Values from 0 to 35999 cover one hour. Values from 36000 to 36009 are used when a leap second occurs. Values from 36010 to 36110 are reserved for future use. A value of 36111 indicates the time point of the event is undefined or unknown.

    See Annex F.3.3.6.4 for additional guidance.
    <Object Identifier> 1.3.6.1.4.1.1206.4.2.18.3.1.4
    <Object Type> C"
    REFERENCE "SAE J2735 DE_TimeMark"
    DEFVAL { 36111 }
    ::= { eclaEntry 4 }

--5.18.3.5 ECLA Ring Current Phase End Time Confidence
eclaRingEndTimeConfidence OBJECT-TYPE
    SYNTAX Integer32 (0..15)
    MAX-ACCESS read-write
    STATUS current
    DESCRIPTION "<Definition> For NTCIP 1202 user clarification, the statistical confidence in the predicted value of the eclaCurrentPhaseLikelyEndTime, as provided by an ECLA.

    See Annex F.3.3.6.5 for additional guidance.
    <Object Identifier> 1.3.6.1.4.1.1206.4.2.18.3.1.5
    <Object Type> C"
    REFERENCE "SAE J2735 DE_TimeIntervalConfidence"
    DEFVAL { 0 }
    ::= { eclaEntry 5 }

--5.19.3.6 ECLA Ring Next Phase
eclaRingNextPhase OBJECT-TYPE
    SYNTAX Integer32 (0..255)
    MAX-ACCESS read-write
    STATUS current
    DESCRIPTION "<Definition> The phase number for the phase is expected to be committed as the next phase in the ring, as provided by an ECLA.  
    
    This value shall not exceed the maxPhases object value. A value of zero indicates that the ECLA is currently unable to provide the information. 
    <Object Identifier> 1.3.6.1.4.1.1206.4.2.18.3.1.6
    <Object Type> C"
    DEFVAL { 0 }
    ::= { eclaEntry 6 }

--5.19.4 ECLA Input Block
eclaInputBlock OBJECT-TYPE
    SYNTAX       OCTET STRING
    MAX-ACCESS   read-write
    STATUS	     current
    DESCRIPTION  "<Definition> An octet string of data required from an ECLA for an ASC to determine when the current phases are expected to terminate their green indications and what phases are expected to be serviced next. This object is used for the ECLA to input into the ASC in a bandwidth efficient manner.

eclaInputData ::= SEQUENCE {  
    eclaDataTimestamp.0              Integer32 (0..36611),
    eclaRingCurrentPhase.x           Integer32 (0..255),
    eclaRingGreenMinEndTime.x        Integer32 (0..36611),
    eclaRingGreenMaxEndTime.x        Integer32 (0..36611),
    eclaRingGreenLikelyEndTime.x     Integer32 (0..36611),
    eclaRingEndTimeConfidence.x      Integer32 (0..36611),
    eclaRingNextPhase.x              Integer32 (0..255)
}

where:
    x is the sequenceRingNumber in the eclaInputTable.
    
    <Object Identifier> 1.3.6.1.4.1.1206.4.2.18.4
    <Object Type> C"
::= { ecla 4 }

--5.19 ASC SMU Monitoring
ascSmu OBJECT IDENTIFIER
    ::= { asc 19 }

--5.19.1 Signal Monitoring Unit Table
ascSmuTable OBJECT-TYPE
    SYNTAX SEQUENCE OF AscSmuTableEntry
    MAX-ACCESS not-accessible
    STATUS current
    DESCRIPTION "<Definition> A table containing channel information from the signal monitoring unit in the cabinet. The number of rows in this table is equal to three times the value of the maxChannels.
    <TableType> static
    <Object Identifier> 1.3.6.1.4.1.1206.4.2.19.1"
    ::= { ascSmu 1 }

ascSmuTableEntry OBJECT-TYPE
    SYNTAX AscSmuTableEntry
    MAX-ACCESS not-accessible
    STATUS current
    DESCRIPTION "<Definition> A row of information for each channel output provided by the signal monitoring unit in the cabinet.
    <Object Identifier> 1.3.6.1.4.1.1206.4.2.19.1.1"
    INDEX { channelNumber, ascSmuChannelOutput }
    ::= { ascSmuTable 1 }

AscSmuTableEntry ::= SEQUENCE {
    ascSmuChannelOutput Integer32,
    ascSmuVoltage       Integer32,
    ascSmuCurrent       Integer32 }

--5.19.1.1 Signal Monitoring Unit Output Index
ascSmuChannelOutput OBJECT-TYPE
    SYNTAX Integer32 (1..3)
    UNITS "output"
    MAX-ACCESS not-accessible
    STATUS current
    DESCRIPTION "<Definition> The different outputs for a channel.
    <Object Identifier> 1.3.6.1.4.1.1206.4.2.19.1.1.1"
    ::= { ascSmuTableEntry 1 }

-- 5.19.1.2 Signal Monitoring Unit Channel Voltage
ascSmuVoltage OBJECT-TYPE
    SYNTAX Integer32 (0..255)
    UNITS "VAC RMS or VDC"
    MAX-ACCESS read-only
    STATUS current
    DESCRIPTION "<Definition> This object shall describe the voltage measured for the
    channel and output type in this row as reported by the signal monitoring unit and measured in
    0 to 254 VAC RMS or from 0 to 50 VDC RMS for DC cabinets. A value of 255 indicates
   that the value is unknown or no measurement was made.
    <Object Identifier> 1.3.6.1.4.1.1206.4.2.19.1.1.3
    <Object Type> S"
    ::= { ascSmuTableEntry 3 }

-- 5.19.1.3 Signal Monitoring Unit Channel Current
ascSmuCurrent OBJECT-TYPE
    SYNTAX Integer32 (0..65535)
    UNITS "milliamperes"
    MAX-ACCESS read-only
    STATUS current
    DESCRIPTION "<Definition> This object shall describe the current measured for the
    channel and output type in this row as reported by the signal monitoring unit and measured in
   milliamperes from 0 to 65000 mA. A value of 65535 indicates
   that the value is unknown or no measurement was made.
    <Object Identifier> 1.3.6.1.4.1.1206.4.2.19.1.1.4
    <Object Type> S"
    ::= { ascSmuTableEntry 4 }


-- 5.20  Signal Phase and Timing
saeNtcip OBJECT IDENTIFIER ::= { devices 17 }

spat OBJECT IDENTIFIER
    ::= { saeNtcip 1 }

-- This defines a node for supporting signal phase and timing objects for a connected vehicle environment.

--7.2.1 Intersection Status
spatStatus OBJECT-TYPE
    SYNTAX Integer32 (0..65535)
    MAX-ACCESS read-only
    STATUS deprecated
    DESCRIPTION "<Definition> For NTCIP 1202 user clarification, if a mode is enabled or active, the associated bit shall be set to (1). The definition of the term 'recent' is defined by the system in use. Bit 0 is equal to Bit 0 of the BIT STRING of DE_IntersectionStatusObject, Bit 1 is equal to Bit 1, etc.
Bit 0: Enabled when unitControlStatus is remoteManualControl (9) or localManualControl (10)
Bit 1: Enabled when Bit 4: Stop Time in unitAlarmStatus2 is TRUE
Bit 2: Enabled when unitFlashStatus is other (1), faultMonitor (5) or mmu (6)
Bit 3: Enabled when the preemptState for any preempt is any value other than other (1), notActive (2), or notActiveWithCall (3).
Bit 4: Enabled if the CU is servicing a signal priority request.
Bit 5: Enabled if the CU is operating in fixedTime mode. This bit and bit 6 are mutually exclusive.
Bit 6: Enabled if the CU is operating in an actuated mode. This bit and bit 5 are mutually exclusive.
Bit 7: Enabled if the unitFlashStatus is automatic (3), localManual (4) or in startup (7)
Bit 8: Controller failure or failure in operation.
Bit 9: Reserved
Bit 10: Enabled if a spatMapActivationCode value has changed within the previous two coordination cycles.
Bit 11: Enabled if the current cycle is the first cycle that a new set of enabledLanesBits is used.
Bit 12: Enabled if the mapActivatePlanError is any value other than none (2).
Bit 13: Enabled if any spatPortStatus object is any value other than normal (3).
    <Object Identifier> 1.3.6.1.4.1.1206.4.2.17.1.1"
    REFERENCE "SAE J2735 DE_IntersectionStatusObject"
    ::= { spat 1 }

--7.2.2 Maximum SPaT Speed Advisories
maxAdvisorySpeeds OBJECT-TYPE
    SYNTAX Integer32 (0..16)
    UNITS "advisory"
    MAX-ACCESS read-only
    STATUS deprecated
    DESCRIPTION "<Definition> This object contains the maximum number of movement speed advisory entries this CU supports. This object indicates the maximum rows which shall appear in the advisorySpeedTable object.
    <Object Identifier> 1.3.6.1.4.1.1206.4.2.17.1.2"
    ::= { spat 2 }

--7.2.3 SPaT Speed Advisories Table
advisorySpeedTable OBJECT-TYPE
    SYNTAX SEQUENCE OF AdvisorySpeedEntry 
    MAX-ACCESS not-accessible
    STATUS deprecated
    DESCRIPTION "<Definition> This table contains speed advisories for a specific movement at a signalized intersection. The number of rows in this table is equal to the maxAdvisorySpeeds object.
    <TableType> static
    <Object Identifier> 1.3.6.1.4.1.1206.4.2.17.1.3"
    ::= { spat 3 }

advisorySpeedEntry OBJECT-TYPE
    SYNTAX AdvisorySpeedEntry
    MAX-ACCESS not-accessible
    STATUS deprecated
    DESCRIPTION "<Definition> Speed advisory information for a specific movement at a signalized intersection.
    <Object Identifier> 1.3.6.1.4.1.1206.4.2.17.1.3.1"
    INDEX  { channelNumber, advisorySpeedIndex }
    ::= { advisorySpeedTable 1 }

AdvisorySpeedEntry::= SEQUENCE {
    advisorySpeedIndex      INTEGER,
    advisorySpeedType       INTEGER,
    advisorySpeedAdvice     INTEGER,
    advisorySpeedZoneLength INTEGER,
    advisorySpeedClass      INTEGER,
    advisorySpeedConfidence INTEGER }

--7.2.3.1   SPaT Speed Advisory Index
advisorySpeedIndex OBJECT-TYPE
    SYNTAX Integer32 (1..16)
    UNITS "number"
    MAX-ACCESS not-accessible
    STATUS deprecated
    DESCRIPTION "<Definition> The advisory speed index for objects in this row. This value shall not exceed the maxAdvisorySpeeds object value.
    <Object Identifier> 1.3.6.1.4.1.1206.4.2.17.1.3.1.1"
    ::= { advisorySpeedEntry 1 }

--7.2.3.2   SPaT Movement Advisory Speed Type
advisorySpeedType OBJECT-TYPE
    SYNTAX INTEGER { none (0),
                 greenwave (1),
                 ecoDrive (2),
                 transit (3) }
    MAX-ACCESS read-write
    STATUS deprecated
    DESCRIPTION "<Definition> For NTCIP 1202 user clarification, the type of speed advisory provided for this movement, such as greenwave or ecoDrive.
    <Object Identifier> 1.3.6.1.4.1.1206.4.2.17.1.3.1.2"
    REFERENCE "SAE J2735 DE_AdvisorySpeedType"
    DEFVAL { none }
    ::= { advisorySpeedEntry 2 }

--7.2.3.3   SPaT Movement Advisory Speed Advice
advisorySpeedAdvice OBJECT-TYPE
    SYNTAX Integer32 (0..500)
    MAX-ACCESS read-write 
    STATUS deprecated
    DESCRIPTION "<Definition> For NTCIP 1202 user clarification, the advisory speed for this movement.
    <Object Identifier> 1.3.6.1.4.1.1206.4.2.17.1.3.1.3"
    REFERENCE "SAE J2735 DE_SpeedAdvice"
    DEFVAL { 500 }
    ::= { advisorySpeedEntry 3 }

--7.2.3.4   SPaT Movement Advisory Speed Zone
advisorySpeedZoneLength OBJECT-TYPE
    SYNTAX Integer32 (0..10000)
    MAX-ACCESS read-write 
    STATUS deprecated
    DESCRIPTION "<Definition> For NTCIP 1202 user clarification, the distance upstream from the stopbar for which the advisory speed is recommended.
    <Object Identifier> 1.3.6.1.4.1.1206.4.2.17.1.3.1.4"
    REFERENCE "SAE J2735 DE_ZoneLength"
    ::= { advisorySpeedEntry 4 }

--7.2.3.5   SPaT Movement Advisory Speed Restriction Class
advisorySpeedClass OBJECT-TYPE
    SYNTAX Integer32 (0..255)
    MAX-ACCESS read-write
    STATUS deprecated
    DESCRIPTION "<Definition> For NTCIP 1202 user clarification, the mapUserClassId value to which the advisory speed applies to. A value of zero indicates that advisory speed applies to all vehicle types.
    <Object Identifier> 1.3.6.1.4.1.1206.4.2.17.1.3.1.5"
    REFERENCE "SAE J2735 DE_RestrictionClassID"
    DEFVAL { 0 }
    ::= { advisorySpeedEntry 5 }

--7.2.3.6   SPaT Movement Advisory Speed Confidence
advisorySpeedConfidence OBJECT-TYPE
    SYNTAX INTEGER { unavailable (0), -- Not Equipped or unavailable 
                 prec100ms (1), -- 100 meters / sec 
                 prec10ms (2), -- 10 meters / sec 
                 prec5ms (3), -- 5 meters / sec 
                 prec1ms (4), -- 1 meters / sec 
                 prec0-1ms (5), -- 0.1 meters / sec 
                 prec0-05ms (6), -- 0.05 meters / sec 
                 prec0-01ms (7) }
    MAX-ACCESS read-write 
    STATUS deprecated
    DESCRIPTION "<Definition> For NTCIP 1202 user clarification, a confidence value for the advisorySpeedAdvice value.
    <Object Identifier> 1.3.6.1.4.1.1206.4.2.17.1.3.1.6"
    REFERENCE "SAE J2735 DE_SpeedConfidence"
    ::= { advisorySpeedEntry 6 }

--7.2.4 Maximum SPaT Movement Maneuvers
maxMovementManeuvers OBJECT-TYPE
    SYNTAX Integer32 (1..16)
    UNITS "maneuver"
    MAX-ACCESS read-only
    STATUS deprecated
    DESCRIPTION "<Definition> This object contains the maximum number of maneuvers for a movement this CU supports for a channel. This object indicates the maximum rows which shall appear in the movementManeuverTable object.
    <Object Identifier> 1.3.6.1.4.1.1206.4.2.17.1.4"
    ::= { spat 4 }

--7.2.5 SPaT Movement Maneuvers Table
movementManeuverTable OBJECT-TYPE
    SYNTAX SEQUENCE OF MovementManeuverEntry 
    MAX-ACCESS not-accessible
    STATUS deprecated
    DESCRIPTION "<Definition> This table contains the allowable maneuvers for a specific movement and channel at a signalized intersection. The number of rows in this table is equal to the maxMovementManeuvers object.
    <TableType> static
    <Object Identifier> 1.3.6.1.4.1.1206.4.2.17.1.5"
    ::= { spat 5 }

movementManeuverEntry OBJECT-TYPE
    SYNTAX MovementManeuverEntry
    MAX-ACCESS not-accessible
    STATUS deprecated
    DESCRIPTION "<Definition> Allowable maneuvers information for a specific movement at a signalized intersection.
    <Object Identifier> 1.3.6.1.4.1.1206.4.2.17.1.5.1"
    INDEX  { channelNumber, movementManeuverIndex }
    ::= { movementManeuverTable 1 }

MovementManeuverEntry::= SEQUENCE {
    movementManeuverIndex           INTEGER, --deprecated
    movementManeuverId              INTEGER, --deprecated
    movementManeuverState           INTEGER, --deprecated
    movementManeuverQueue           INTEGER, --deprecated
    movementManeuverStorage         INTEGER, --deprecated
    movementManeuverStatus          INTEGER, --deprecated
    movementManeuverQueueDetector   OCTET STRING, --deprecated
    movementManeuverPedPresence     OCTET STRING, --deprecated
    movementManeuverBicyclePresence OCTET STRING, --deprecated
    movementManeuverGreenType       INTEGER, --deprecated
    movementManeuverGreenIncluded   OCTET STRING } --deprecated

--7.2.5.1   SPaT Movement Maneuver Number
movementManeuverIndex OBJECT-TYPE
    SYNTAX Integer32 (1..16)
    MAX-ACCESS not-accessible
    STATUS deprecated
    DESCRIPTION "<Definition> For NTCIP 1202 user clarification, a connection index for a lane to lane connection for the movement indexed to a specific channel.
    <Object Identifier> 1.3.6.1.4.1.1206.4.2.17.1.5.1.1"
    ::= { movementManeuverEntry 1 }

--7.2.5.2   SPaT Movement Maneuver Identifier
movementManeuverId OBJECT-TYPE
    SYNTAX Integer32 (0..255)
    MAX-ACCESS read-write
    STATUS deprecated
    DESCRIPTION "<Definition> This object is used to uniquely identify a lane to lane connection for the intersection. Can be used to relate SPaT data to a lane defined in the MAP messages. A value of zero indicates that the row is disabled and all other values in the row are not valid.
    <Object Identifier> 1.3.6.1.4.1.1206.4.2.17.1.5.1.2"
    REFERENCE "SAE J2735 DF_ConnectionManeuverAssist and DE_LaneConnectionID"
    ::= { movementManeuverEntry 2 }

--7.2.5.3   SPaT Movement Maneuver State
movementManeuverState OBJECT-TYPE
    SYNTAX Integer32 (0..9)
    MAX-ACCESS read-only
    STATUS deprecated
    DESCRIPTION "<Definition> For NTCIP 1202 user clarification, this object defines the state of a specific movement maneuver (lane connection) at the intersection, unlike signalState, which defines the general state of a channel. This object value is determined as follows where Column A is the movementManeuverGreenType, Column B is the movementManeuverGreenIncluded, and Column C is the channel output for the channelNumber:
+-----------------+-----------------+-----+-----------------+--------+
| movementManeuver|                 |     |                 |        |
|      State      |        A        |  B  |        C        | Notes  |
+-----------------+-----------------+-----+-----------------+--------+
| unavailable (0) |       Any       | Any |   Unavailable   |        |
| 1 - See Note G  |       Any       | Any |   See Note A    |        |
| 2 - See Note G  |   flashRed (5)  |  0  |   Green or Red  |        |
| 3 - See Note G  |       Any       | Any |       Red       | Note B |
| 4 - See Note G  |       N/A       | N/A |       N/A       |        |
| 5 - See Note G  |  permissive (3) |  0  |      Green      |        |
| 5 - See Note G  |  protected (2)  | > 0 |Not Yellow or Red| Note C |
| 6 - See Note G  |  protected (2)  | > 0 |Not Yellow or Red| Note D |
| 6 - See Note G  |  protected (2)  |  0  |      Green      |        |
| 7 - See Note G  |       Any       | Any |      Yellow     | Note E |
| 8 - See Note G  |  protected (2)  | Any |      Yellow     | Note F |
| 9 - See Note G  | flashYellow (4) |  0  | Green or Yellow |        |
+-----------------+-----------------+-----+-----------------+--------+

Note A: Not Green, Yellow or Red.
Note B: If this movement maneuver is controlled by a 4-section head or 5-section head, and the signal indication is 'Red', then this movement maneuver is also considered 'Red'.
Note C: If one or more of the octets in movementManeuverGreenIncluded is NOT 'Red' or is Dark.
Note D: If all octets in movementManeuverGreenIncluded are 'Red'.
Note E: Only if the preceding movementManeuverState was permissive-movement-allowed.
Note F: Only if the preceding movementManeuverState was protected-movement-allowed.
Note G: The definition of the value can be found in SAE J2735 DE_MovementPhaseState.

For example, the object value is '6' if the movementManeuverGreenType is protected (2), and all octets in movementManeuverGreenIncluded (each representing a channelNumber) are 'Red'; OR if the movementManeuverGreenType is protected (2) and the movementManeuverGreenIncluded is 00.
If the movementManeuverTable is used, this object may be exchanged between the ASC and the CV Roadside Process in lieu of the signalState object.
    <Object Identifier> 1.3.6.1.4.1.1206.4.2.17.1.5.1.3"
    REFERENCE "SAE J2735 DE_MovementPhaseState"
    ::= { movementManeuverEntry 3 }

--7.2.5.4   SPaT Movement Queue
movementManeuverQueue OBJECT-TYPE
    SYNTAX Integer32 (0..10000)
    MAX-ACCESS read-only
    STATUS deprecated 
    DESCRIPTION "<Definition> For NTCIP 1202 user clarification, the distance from the stop line at the intersection for this movement to the back edge of the last vehicle in the queue.
    <Object Identifier> 1.3.6.1.4.1.1206.4.2.17.1.5.1.4"
    REFERENCE "SAE J2735 DF_ConnectionManeuverAssist and DE_ZoneLength"
    DEFVAL { 0 }
    ::= { movementManeuverEntry 4 }

--7.2.5.5   SPaT Movement Storage
movementManeuverStorage OBJECT-TYPE
    SYNTAX Integer32 (0..10000)
    MAX-ACCESS read-only
    STATUS deprecated
    DESCRIPTION "<Definition> For NTCIP 1202 user clarification, the distance with a high probability for successfully executing the connecting maneuver between the approach lane and the egress lane during the current cycle.
    <Object Identifier> 1.3.6.1.4.1.1206.4.2.17.1.5.1.5"
    REFERENCE "SAE J2735 DF_ConnectionManeuverAssist and DE_ZoneLength"
    DEFVAL { 0 }
    ::= { movementManeuverEntry 5 }

--7.2.5.6   SPaT Movement Assist Status
movementManeuverStatus OBJECT-TYPE
    SYNTAX Integer32 (0..255)
    MAX-ACCESS read-only
    STATUS deprecated
    DESCRIPTION "<Definition> For NTCIP 1202 user clarification, this object defines the options for traveler connections through an intersection.
Bit 7:  Reserved
Bit 6:  Reserved
Bit 5:  Reserved
Bit 4:  Reserved
Bit 3:  Reserved
Bit 2:  Reserved
Bit 1:  Status bit set to TRUE (1) if ANY pedestrians or bicyclists are detected in a conflicting movement. Set to FALSE (0) if there is a high certainty no pedestrians or bicyclists are present.
Bit 0:  Set to TRUE (1) if vehicles for this movement maneuver have to stop on the stop-line and not enter the intersection.
A SET of a 'reserved' bit of Bit 1 to a value other than zero (0) shall return a badValue(3) error.
    <Object Identifier> 1.3.6.1.4.1.1206.4.2.17.1.5.1.6"
    REFERENCE "SAE J2735 DE_WaitOnStopline and DE_PedestrianBicycleDetect"
    ::= { movementManeuverEntry 6 }

--7.2.5.7   SPaT Movement Queue Detector
movementManeuverQueueDetector OBJECT-TYPE
    SYNTAX OCTET STRING
    MAX-ACCESS read-write
    STATUS deprecated
    DESCRIPTION "<Definition> Each octet in this octet string represents a vehicle detector number (vehicleDetectorNumber) in the vehicleDetectorTable that provides the data to determine movementManeuverQueue. A value of zero0 indicates that no additional vehicle detectors follow in the octet string.
    <Object Identifier> 1.3.6.1.4.1.1206.4.2.17.1.5.1.7"
    ::= { movementManeuverEntry 7 }

--7.2.5.8   SPaT Movement Pedestrian Presence
movementManeuverPedPresence OBJECT-TYPE
    SYNTAX OCTET STRING
    MAX-ACCESS read-write
    STATUS deprecated
    DESCRIPTION "<Definition> Each octet in this octet string represents a pedestrian detector number (pedestrianDetectorNumber) in the pedestrianDetectorTable (with Bit 0 in the corresponding pedestrianDetectorOptions Enabled) whose detection status indicates a pedestrian is detected in the pedestrian crossing that conflicts with this movementManeuverIndex. For example, an octet string of 01 03 indicates that if pedestrian detector 1 or pedestrian detector 3 is active/ON, then the presence of a pedestrian has been detected that conflicts with this movementManeuverIndex. If a pedestrian is detected by any pedestrianDetectorNumber in the octet string, Bit 1 in movementManeuverStatus shall be SET to TRUE (1).
    <Object Identifier> 1.3.6.1.4.1.1206.4.2.17.1.5.1.8"
    ::= { movementManeuverEntry 8 }

--7.2.5.9   SPaT Movement Bicycle Presence
movementManeuverBicyclePresence OBJECT-TYPE
    SYNTAX OCTET STRING
    MAX-ACCESS read-write
    STATUS deprecated
    DESCRIPTION "<Definition> Each octet in this octet string represents a vehicle detector number (vehicleDetectorNumber) in the vehicleDetectorTable that when active/ON indicates that a bicyclist is detected that conflicts with this movementManeuverIndex. If a bicyclist is detected by any of the  vehicleDetectorNumber in the octet string, Bit 1 in movementManeuverStatus shall be SET to TRUE (1). For example, an octet string of 02 06 indicates that if vehicle detector 2 or vehicle detector 6 is active/ON, then the presence of a bicyclist has been detected that conflicts with this movementManeuverIndex.
    <Object Identifier> 1.3.6.1.4.1.1206.4.2.17.1.5.1.9"
    ::= { movementManeuverEntry 9 }

--7.2.5.10  SPaT Movement Type
movementManeuverGreenType OBJECT-TYPE
    SYNTAX INTEGER { other (1),
                 protected (2),
                 permissive (3),
                 flashYellow (4),
                 flashRed (5) }
    MAX-ACCESS read-write
    STATUS deprecated
    DESCRIPTION "<Definition> This object defines the movementManeuverState for this specific movement maneuver when the channel output is Green. This object is used to support the generation of SPAT data.
other: the allowed movement controlled by this channel is not defined by this standard.
protected: indicates that at least a portion of the green movement occurs in protected mode.
permissive: indicates that the green movement occurs in permissive mode, that is, any turns are permitted to be made only after yielding to pedestrians and/or any opposing traffic.
flashYellow: indicates that a vehicle may proceed but with caution after yielding to pedestrians and/or any conflicting traffic. Includes flashing yellow arrows.
flashRed: indicates that a vehicle may proceed after stopping and yielding to pedestrians and/or any conflicting traffic. Includes flashing red arrows.
Note there is a similar object called channelGreenType that identifies the state when the channel output is Green in general.
    <Object Identifier> 1.3.6.1.4.1.1206.4.2.17.1.5.1.10"
    ::= { movementManeuverEntry 10 }

--7.2.5.11  SPaT Movement Included Movements
movementManeuverGreenIncluded OBJECT-TYPE
    SYNTAX OCTET STRING
    MAX-ACCESS read-write
    STATUS deprecated
    DESCRIPTION "<Definition> If the movementManeuverGreenType for this movement maneuver is 'protected (2)', this object is used to indicate if and when this movement maneuver is in permissive mode. This object is used to support the generation of SPAT data and defines the movementManeuverState for this movement maneuver only IF the maneuverMovementGreenType is 'protected (2)'. Each octet in the octet string represents a conflicting or opposing channelNumber, which if the status for any octet in the octet string is NOT Channel Red or is dark, then the movementManeuverState for this movement maneuver is 'permissive-Movement-Allowed (5)' when the status for this channel is channel Green. Otherwise, the movementManeuverState for this movement maneuveris 'protected-Movement-Allowed (6)' when the status for this channel is channel Green.

    If movementManeuverGreenType in this row is not 'protected (2)', then this object value is ignored.

It is assumed that a clearance state following a movementManeuverState of 'permissive movement allowed' will be a movementManeuverState of 'permissive clearance', and a clearance state following a movementManeuverState of 'protected movement allowed' will be a movementManeuverState of 'protected clearance'.

For example, assume channelNumber 1 represents a northbound left turn, while channelNumber 2 is a southbound through movement. A channelGreenType.1 of 'protected (2)' and channelGreenIncluded.1 of '02' indicates that if the status of channelNumber 2 is NOT Channel Red or is dark, then the movementManeuverState for the movement associated with channelNumber.1 is 'permissive-Movement-Allowed (5)' when the status for channelNumber.1 is channel Green. Otherwise, the movementManeuverState for the movement associated with channelNumber.1 is 'protected-Movement-Allowed (6)' when the status for this channel is channel Green.
    <Object Identifier> 1.3.6.1.4.1.1206.4.2.17.1.5.1.11"
    ::= { movementManeuverEntry 11 }

--5.20.1 SPaT Enabled Lanes Status
spatEnabledLanesStatus OBJECT-TYPE 
    SYNTAX OCTET STRING
    MAX-ACCESS read-only
    STATUS current
    DESCRIPTION "<Definition> Each octet within the octet string contains the (revocable) lane identifier that is currently enabled. Lanes that may not always be ACTIVE (enabled) should be identified as a revocable lane in the MAP message for the intersection.
    <Object Identifier> 1.3.6.1.4.1.1206.4.2.17.1.6"
    REFERENCE "SAE J2735 DF_EnabledLaneList"
    ::= { spat 6 }

--7.2.7 SPaT Signal Status Table
signalStatusTable OBJECT-TYPE
    SYNTAX SEQUENCE OF SignalStatusEntry
    MAX-ACCESS not-accessible
    STATUS deprecated
    DESCRIPTION "<Definition> This table contains signal status information for a signalized intersection. The number of rows in this table is equal to the maxChannels object.
    <TableType> static
    <Object Identifier> 1.3.6.1.4.1.1206.4.2.17.1.7"
    ::= { spat 7 }

signalStatusEntry OBJECT-TYPE
    SYNTAX SignalStatusEntry
    MAX-ACCESS not-accessible
    STATUS deprecated
    DESCRIPTION "<Definition> The status of a specific signal group.
    <Object Identifier> 1.3.6.1.4.1.1206.4.2.17.1.7.1"
    INDEX  { channelNumber }
    ::= { signalStatusTable 1 }

SignalStatusEntry::= SEQUENCE {
    signalState               INTEGER, --deprecated
    signalStateMinEndTick     INTEGER, --deprecated
    signalStateMaxEndTick     INTEGER, --deprecated
    signalStateLikelyEndTick  INTEGER, --deprecated
    signalStateTickConfidence INTEGER, --deprecated
    signalNextTick            INTEGER } --deprecated

--7.2.7.1   SPaT Event State
signalState OBJECT-TYPE
    SYNTAX Integer32 (0..9)
    MAX-ACCESS read-only
    STATUS deprecated
    DESCRIPTION "<Definition> For NTCIP 1202 user clarification, this object value defines the movement state (e.g., permitted, protected) of a channel. This object is determined as follows where Column A is the channelGreenType, Column B is the channelGreenIncluded, and Column C is the channel output for the channelNumber:

+-----------------+-----------------+-----+-----------------+--------+
|   signalState   |        A        |  B  |        C        | Notes  |
+-----------------+-----------------+-----+-----------------+--------+
| unavailable (0) |       Any       | Any |   Unavailable   |        |
| 1 - See Note G  |       Any       | Any |   See Note A    |        |
| 2 - See Note G  |   flashRed (5)  |  0  |   Green or Red  | Note B |
| 3 - See Note G  |       Any       | Any |       Red       |        |
| 4 - See Note G  |       N/A       | N/A |       N/A       |        |
| 5 - See Note G  |  permissive (3) |  0  |      Green      |        |
| 5 - See Note G  |  protected (2)  | > 0 |      Green      | Note C |
| 6 - See Note G  |  protected (2)  | > 0 |      Green      | Note D |
| 6 - See Note G  |  protected (2)  |  0  |      Green      |        |
| 7 - See Note G  |       Any       | Any |      Yellow     | Note E |
| 8 - See Note G  |  protected (2)  | Any |      Yellow     | Note F |
| 9 - See Note G  | flashYellow (4) |  0  | Green or Yellow |        |
+-----------------+-----------------+-----+-----------------+--------+

Note A: Not Green, Yellow or Red.
Note B: If this movement state is controlled by a 4-section head or 5-section head, and the signal indication is 'Red', then this movement maneuver is also considered 'Red'.
Note C: If one or more of the octets in channelGreenIncluded is Not 'Red' or is dark.
Note D: If all octets in channelGreenIncluded are 'Red'.
Note E: Only if the preceding signalState was permissive-movement-allowed.
Note F: Only if the preceding signalState was protected-movement-allowed.
Note G: The definition of the value can be found in SAE J2735 DE_MovementPhaseState.

For example, the object value is '6' if the channelGreenType is protected (2), and all octets in channelGreenIncluded (each representing a channelNumber) are 'Red'; OR if the channelGreenType is protected (2) and the channelGreenIncluded is 00.

Note this object provides the movement state of the channel in general, unlike movementManeuverState which defines the movement state of a specific movement maneuver (from what lane to what lane). This object may be exchanged between the ASC and CV Roadside Process if the movementManeuverState is not used.
    <Object Identifier> 1.3.6.1.4.1.1206.4.2.17.1.7.1.1"
    REFERENCE "SAE J2735 DE_MovementPhaseState"
    ::= { signalStatusEntry 1 }

--7.2.7.2   SPaT Signal State Minimum End Time
signalStateMinEndTick OBJECT-TYPE
    SYNTAX Integer32 (0..36001)
    UNITS "tick"
    MAX-ACCESS read-only
    STATUS deprecated
    DESCRIPTION "<Definition> The tick count representing the earliest future time point when the signalState is expected to change, excluding unexpected events such as a preempt request. This object is used with the ascCurrentTick object. The value of this object will remain constant if the predicted future time point of the event does not change. Valid values range from 0 to 35999. A value of 36000 indicates the time point is infinite or beyond the range that can be represented (e.g., the earliest time point is greater than 36000 ticks). A value of 36001 indicates the time point of the event is undefined or unknown.

The maximum reportable time point in the future the event will occur is 35999 deciseconds. To calculate this future time point consumers of this object subtracts signalStateMinEndTick from ascCurrentTick. If this result is negative add 36000 to the result (rollover).
    <Object Identifier> 1.3.6.1.4.1.1206.4.2.17.1.7.1.2"
    DEFVAL { 36001 }
    ::= { signalStatusEntry 2 }

--7.2.7.3   SPaT Signal State Maximum End Time
signalStateMaxEndTick OBJECT-TYPE
    SYNTAX Integer32 (0..36001)
    UNITS "tick"
    MAX-ACCESS read-only
    STATUS deprecated
    DESCRIPTION "<Definition> The tick count representing the latest future time point when the signalState is expected to change, excluding unexpected events such as a preempt request. This object is used with the ascCurrentTick object. The value of this object will remain constant if the predicted future time point of the event does not change. Valid values range from 0 to 35999. A value of 36000 indicates the time point is infinite or beyond the range that can be represented (e.g., the latest time point is greater than 36000 ticks). A value of 36001 indicates the time point of the event is undefined or unknown.

The maximum reportable time point in the future the event will occur is 35999 deciseconds. To calculate this future time point consumers of this object subtracts signalStateMaxEndTick from ascCurrentTick. If this result is negative add 36000 to the result (rollover).
    <Object Identifier> 1.3.6.1.4.1.1206.4.2.17.1.7.1.3"
    DEFVAL { 36001 }
    ::= { signalStatusEntry 3 }

--7.2.7.4   SPaT Signal State Likely Time
signalStateLikelyEndTick OBJECT-TYPE
    SYNTAX Integer32 (0..36001)
    UNITS "tick"
    MAX-ACCESS read-only
    STATUS deprecated
    DESCRIPTION "<Definition> The tick count representing the most likely future time point when the signalState is expected to change, excluding unexpected events such as a preempt request. This object is used with the ascCurrentTick object. The value of this object will remain constant if the predicted future time point of the event does not change. Valid values range from 0 to 35999. A value of 36000 indicates the time point is infinite or beyond the range that can be represented (e.g., the likely time point is greater than 36000 ticks). A value of 36001 indicates the time point of the event is undefined or unknown.

The maximum reportable time point in the future the event will occur is 35999 deciseconds. To calculate this future time point consumers of this object subtracts signalStateLikelyEndTick from ascCurrentTick. If this result is negative add 36000 to the result (rollover).
    <Object Identifier> 1.3.6.1.4.1.1206.4.2.17.1.7.1.4"
    DEFVAL { 36001 }
    ::= { signalStatusEntry 4 }

--7.2.7.5   SPaT Signal State Time Confidence
signalStateTickConfidence OBJECT-TYPE
    SYNTAX Integer32 (0..15)
    MAX-ACCESS read-only
    STATUS deprecated
    DESCRIPTION "<Definition> For NTCIP 1202 user clarification, the statistical confidence in the predicted value of the signalStateLikelyTick.
    <Object Identifier> 1.3.6.1.4.1.1206.4.2.17.1.7.1.5"
    REFERENCE "SAE J2735 DE_TimeIntervalConfidence"
    DEFVAL { 0 }
    ::= { signalStatusEntry 5 }

--7.2.7.6   SPaT Signal Next Tick
signalNextTick OBJECT-TYPE
    SYNTAX Integer32 (0..36001)
    UNITS "tick"
    MAX-ACCESS read-only
    STATUS deprecated
    DESCRIPTION "<Definition> The tick count representing the most likely future time point when the movement is expected to be allowed to move again (e.g., green), excluding unexpected events such as a preempt request. This object is used with the ascCurrentTick object. The value of this object will remain constant if the predicted future time point of the event does not change. Valid values range from 0 to 35999. A value of 36000 indicates the time point is infinite or beyond the range that can be represented (e.g., the time point is greater than 36000 ticks). A value of 36001 indicates the time point of the event is undefined or unknown.
If the current signalState is not a red light or in a clearance interval, then a value of 36001 is used.

The maximum reportable time point in the future the event will occur is 35999 deciseconds. To calculate this future time point consumers of this object subtracts signalNextTick from ascCurrentTick. If this result is negative add 36000 to the result (rollover).
    <Object Identifier> 1.3.6.1.4.1.1206.4.2.17.1.7.1.6"
    DEFVAL { 36001 }
    ::= { signalStatusEntry 6 }

--7.2.8 SPaT Signal Status Block
signalStatusBlock OBJECT-TYPE
    SYNTAX ITSOerString 
    MAX-ACCESS read-write
    STATUS deprecated 
    DESCRIPTION "<Definition> An OER encoded string of the signalStatusTable
        structure as defined below. This object is used for uploading
        configuration data from the ASC in a bandwidth efficient manner.

        The following data is repeated for each channel. OPTIONAL fields shall
        be present only if there are changes in the data values and if the
        data is supported by the implementation. The OPTIONAL fields shall be
        omitted for any data that has not changed from a previously
        transmitted object or not supported by the implementation.

        signalStatus ::= SEQUENCE {  
        ascCurrentTick.0, -- @NTCIP1202-v03, Bytes 1 & 2
        channelData       SEQUENCE OF channelSignalData   OPTIONAL
        }

        channelSignalData ::== SEQUENCE {
        channelNumber.x                       -- 1 BYTE @NTCIP1202-v03
        signalStatusBitMask.x                 -- 1 BYTE
        signalState.x               OPTIONAL, -- 1 BYTE @NTCIP1202-v03
        signalStateMinEndTick.x     OPTIONAL, -- 2 BYTES @NTCIP1202-v03
        signalStateMaxEndTick.x     OPTIONAL, -- 2 BYTES @NTCIP1202-v03
        signalStateLikelyEndTick.x  OPTIONAL, -- 2 BYTES @NTCIP1202-v03
        signalStateTickConfidence.x OPTIONAL, -- 1 BYTE @NTCIP1202-v03
        signalNextTick.x            OPTIONAL  -- 2 BYTES @NTCIP1202-v03
        }

        where:

        signalStatusBitMask is a bit mask (INTEGER (0..255)) defining the
            data that follows in the OerString. When a bit=1, the data is
            included in the OerString. If a bit=0, the corresponding data is
            omitted and not in the OER string.
            Bit 7: Reserved
            Bit 6: Reserved
            Bit 5: signalNextTick - reference tick to next green state data is
                    present. Values are 0..36001. 36001 means could not
                    calculate or undefined.
            Bit 4: signalStateTickConfidence data for this channel is present
                    (1 byte).
            Bit 3: signalStateLikelyEndTick data for this channel is present
                    (2 bytes). Values are 0..36001. 36001 means could not
                    calculate or undefined.
            Bit 2: signalStateMaxEndTick data for this channel is present
                    (2 bytes). Values are 0..36001. 36001 means could not
                    calculate or undefined.
            Bit 1: signalStateMinEndTick data for this channel is present
                    (2 bytes). Values are 0..36001. 36001 means could not
                    calculate or undefined.
            Bit 0: signalState data for this channel is present (1 byte).
    <Object Identifier> 1.3.6.1.4.1.1206.4.2.17.1.8"
    ::= { spat 8 }

--7.2.9 SPaT Movement Maneuver Status Block
movementManeuverStatusBlock OBJECT-TYPE
    SYNTAX ITSOerString
    MAX-ACCESS read-write
    STATUS deprecated
    DESCRIPTION "<Definition> An OER encoded string of the
        movementManeuverTable structure as defined below. This object is
        used for uploading configuration data from the ASC in a bandwidth
        efficient manner.
        The following data is repeated for each channel. OPTIONAL fields
        shall be present only if there are changes in the data values and if
        the data is supported by the implementation. The OPTIONAL fields
        shall be omitted for any data that has not changed from a previously
        transmitted object or not supported by the implementation.

        movementManeuverStatus ::= SEQUENCE {
        ascCurrentTick.0, -- @NTCIP1202-v03, Bytes 1 & 2
        movementManeuverData SEQUENCE OF movementManeuverStatusData
        OPTIONAL
        }
        movementManeuverStatusData ::== SEQUENCE {
        channelNumber.x                     -- 1 BYTE @NTCIP1202-v03
        movementManeuverCount.x             -- 1 BYTE
        movementManeuverIndex.x.y           -- 1 BYTE @NTCIP1202-v03
        movementManeuverBitMask.x.y         -- 1 BYTE
        movementManeuverState.x.y OPTIONAL, -- 1 BYTE @NTCIP1202-v03

        movementManeuverQueue.x.y   OPTIONAL, -- 2 BYTES @NTCIP1202-v03
        movementManeuverStorage.x.y OPTIONAL, -- 2 BYTES @NTCIP1202-v03
        waitOnStop.x.y              OPTIONAL, -- 1 BYTE
        pedBicycleDetect.x.y        OPTIONAL, -- 1 BYTE
        }

        where:
        movementManueuverCount is an INTEGER (0..255) defining the number of
        movement maneuver that follows for this channel; and
        movementManeuverBitMask is a bit mask (INTEGER (0..255)) defining
        the data that follows in the ITSOerString. When a bit=1, the data is
        included in the ITSOerString. If a bit=0, the corresponding data is
        omitted and not in the OER string.
            Bit 7: Reserved
            Bit 6: Reserved
            Bit 5: Reserved
            Bit 4: pedBicycleDetect data for this channel and
                    movementManeuverIndex is present (1 byte).
            Bit 3: waitOnStop data for this channel and movementManeuverIndex
                    is present (1 byte).
            Bit 2: movementManeuverStorage data for this channel and
                    movementManeuverIndex is present (2 bytes).
            Bit 1: movementManeuverQueue data for this channel and
                    movementManeuverIndex is present (2 bytes).
            Bit 0: movementManeuverState data for this channel and
                    movementManeuverIndex is present (1 byte).

        waitOnStop is (INTEGER (0..255)) and is equal to 1 if vehicles for
        this movement maneuver have to stop on the stop-line and not enter
        the intersection, and equal to 2 if the vehicles do not.
        pedBicycleDetect is (INTEGER (0..255)) and is equal to 1 if ANY
        pedestrians or bicyclists are detected in a conflicting movement,
        and is equal to 2 if there is a high certainty no pedestrians or
        bicyclists are present.
    <Object Identifier> 1.3.6.1.4.1.1206.4.2.17.1.9"
    ::= { spat 9 }

--5.20.2    Intersection Status 
spatStatus2 OBJECT-TYPE
    SYNTAX Integer32 (0..65535)
    MAX-ACCESS read-only
    STATUS current
    DESCRIPTION "<Definition> For NTCIP 1202 user clarification, if a mode is enabled or active, the associated bit shall be set to (1). Bit 0 is equal to Bit 0 of the BIT STRING of DE_IntersectionStatusObject, Bit 1 is equal to Bit 1, etc.

    Bit 15: Reserved.
    Bit 14: Reserved.
    Bit 13: Invalid SPaT. Enabled if any spatPortStatus object is any value other than normal (3), if spatOptions Bit 1 is FALSE, or the spatPortOptions Bit 1 is FALSE.
    Bit 12: Invalid MAP. Enabled if spatOptions Bit 2 is FALSE, or the spatPortOptions Bit 2 is FALSE.
    Bit 11: Reserved. SET to 1.
    Bit 10: Reserved. SET to 1.
    Bit 9: Reserved. SET to 0.
    Bit 8: Failure Mode. Controller failure or failure in operation.
    Bit 7: Standby. Enabled if the unitFlashStatus is automatic (3), startup (7), or preempt (8).
    Bit 6: Traffic Dependent. Enabled if the CU is operating in an actuated mode. This bit and Bit 5 cannot both be simultaneously active.
    Bit 5: Fixed Time. Enabled if the CU is operating in fixedTime mode. This is true when every phase in the active sequence is running with a Max Vehicle Recall, a nonActuated split, or is responding to a call to nonactuated input. This bit and Bit 6 cannot both be simultaneously active.
    Bit 4: Signal Priority. Enabled when Bit 8: Priority Call of shortAlarmStatusv4 is True. 
    Bit 3: Preempt. Enabled when Bit 0: Preempt Active of shortAlarmStatusv4 is TRUE and the active preempt's preemptState is any value other than notActive (2) or notActiveWithCall (3). This bit may also be enabled if the active preempt's preemptState is other (1) and determinate.
    Bit 2: Failure Flash. Enabled when unitFlashStatus is localManual (4), controllerFaultFlash (5), or smu (6). 
    This bit may also be enabled if Bit 0: Preempt Active of shortAlarmStatusv4 is TRUE and the active preempt's preemptState is other (1) and indeterminate.
    Bit 1: Stop Time. Enabled when Bit 7: Stop Time in shortAlarmStatusv4 is TRUE.
    Bit 0: Manual Control. Enabled when unitControlStatus is remoteManualControl (9) or localManualControl (10).

The default bit value for Bits 10 and 11 is enabled (1). The default bit value for all other Bits is disabled (0).
See Annex F.3.3.4 for additional guidance.
    <Object Identifier> 1.3.6.1.4.1.1206.4.2.17.1.10
    <Object Type> S"
    REFERENCE "SAE J2735 DE_IntersectionStatusObject"
    DEFVAL { 3072 }
    ::= { spat 10 }

--5.20.3    Maximum Movement Events
maxMovementEvents OBJECT-TYPE
    SYNTAX INTEGER (2..16)
    UNITS "movement"
    MAX-ACCESS read-only
    STATUS current
    DESCRIPTION "<Definition> This object contains the maximum number of movement events for each signal group this CU supports. The first movement event represents the current interval, the second movement event represents the next (future) movement event to follow the current interval.
    <Object Identifier> 1.3.6.1.4.1.1206.4.2.17.1.11
    <Object Type> S"
    ::= { spat 11 }

--5.20.4    SPaT Signal Status Table
signalStatusTable2 OBJECT-TYPE
    SYNTAX SEQUENCE OF SignalStatusEntry2
    MAX-ACCESS not-accessible
    STATUS current
    DESCRIPTION "<Definition> This table contains signal status information for signalized intersections controlled by the CU.
    <TableType> static
    <Object Identifier> 1.3.6.1.4.1.1206.4.2.17.1.12"
    ::= { spat 12 }

signalStatusEntry2 OBJECT-TYPE
    SYNTAX SignalStatusEntry2
    MAX-ACCESS not-accessible
    STATUS current
    DESCRIPTION "<Definition> The status of a specific signal group.
    <Object Identifier> 1.3.6.1.4.1.1206.4.2.17.1.12.1"
    INDEX  { signalGroupEntryNumber, movementEventNumber }
    ::= { signalStatusTable2 1 }

SignalStatusEntry2::= SEQUENCE {
    movementEventNumber        Integer32,
    signalState2               INTEGER,
    signalStateMinEndTick2     Integer32,
    signalStateMaxEndTick2     Integer32,
    signalStateLikelyEndTick2  Integer32,
    signalStateTickConfidence2 Integer32,
    signalStateNextTick2       Integer32,
    signalStateStartTick       Integer32 }

--5.20.4.1  Movement Event Number
movementEventNumber OBJECT-TYPE
    SYNTAX Integer32 (1..16)
    UNITS "number"
    MAX-ACCESS not-accessible
    STATUS current
    DESCRIPTION "<Definition> The movement index for objects in this row. This value shall not exceed the maxMovementEvents object value. Index value 1 contains the value for the current interval and Index value 2 contains the value for the next interval.
    <Object Identifier> 1.3.6.1.4.1.1206.4.2.17.1.12.1.1"
    ::= { signalStatusEntry2 1 }

--5.20.4.2  SPaT Event State
signalState2 OBJECT-TYPE
    SYNTAX INTEGER { other (1),
                 unavailable (2),
                 dark (3), 
                 stopThenProceed (4),
                 stopAndRemain (5),
                 preMovement (6),
                 permissiveMovementAllowed (7),
                 protectedMovementAllowed (8),
                 permissiveClearance (9),
                 protectedClearance (10),
                 cautionConflictingTraffic (11) }
    MAX-ACCESS read-only
    STATUS current 
    DESCRIPTION "<Definition> This object value defines the movement phase state for a signal group ID. movementEventNumber.1 indicates the current movement phase state, and movementEventNumber.2 indicates the next movement phase state. If the movement phase state is unknown, a value of 2 is used.

The movement phase state is determined by agencySignalStateValue.   

See Annex F.3.3.5 for additional guidance.
    <Object Identifier> 1.3.6.1.4.1.1206.4.2.17.1.12.1.2
    <Object Type> S"
    REFERENCE "SAE J2735 DE_MovementPhaseState"
    ::= { signalStatusEntry2 2 }

--5.20.4.3  SPaT Signal State Minimum End Time
signalStateMinEndTick2 OBJECT-TYPE
    SYNTAX Integer32 (0..36111)
    UNITS "ticks"
    MAX-ACCESS read-only
    STATUS current
    DESCRIPTION "<Definition> The tick count representing the earliest future time point when the signalState is expected to change, excluding unexpected events such as a preempt request.  The value of this object will remain constant if the predicted future time point of the event does not change. Values from 0 to 35999 cover one hour. Values from 36000 to 36009 are used when a leap second occurs. Values from 36010 to 36110 are reserved for future use. A value of 36111 indicates the time point of the event is undefined or unknown.

This object is used with the ascCurrentTick2 object. If signalStateMinEndTick2 is greater than ascCurrentTick2 then the end time is in the current hour. If signalStateMinEndTick2 is less than ascCurrentTick2 then the time is in the next hour.

See Annex F.3.3.6.2 for additional guidance.
    <Object Identifier> 1.3.6.1.4.1.1206.4.2.17.1.12.1.3
    <Object Type> S"
    REFERENCE "SAE J2735 DE_TimeMark"
    DEFVAL { 36111 }
    ::= { signalStatusEntry2 3 }

--5.20.4.4  SPaT Signal State Maximum End Time
signalStateMaxEndTick2 OBJECT-TYPE
    SYNTAX Integer32 (0..36111)
    UNITS "tick"
    MAX-ACCESS read-only
    STATUS current
    DESCRIPTION "<Definition> The tick count representing the latest future time point when the signalState is expected to change, excluding unexpected events such as a preempt request. The value of this object will remain constant if the predicted future time point of the event does not change. Values from 0 to 35999 cover one hour. Values from 36000 to 36009 are used when a leap second occurs. Values from 36010 to 36110 are reserved for future use. A value of 36111 indicates the time point of the event is undefined or unknown.

This object is used with the ascCurrentTick2 object. If signalStateMaxEndTick2 is greater than ascCurrentTick2 then the end time is in the current hour. If signalStateMaxEndTick2 is less than ascCurrentTick2 then the time is in the next hour.

See Annex F.3.3.6.3 for additional guidance.
    <Object Identifier> 1.3.6.1.4.1.1206.4.2.17.1.12.1.4
    <Object Type> S"
    REFERENCE "SAE J2735 DE_TimeMark"
    DEFVAL { 36111 }
    ::= { signalStatusEntry2 4 }

--5.20.4.5  SPaT Signal State Likely Time
signalStateLikelyEndTick2 OBJECT-TYPE
    SYNTAX Integer32 (0..36111)
    UNITS "tick"
    MAX-ACCESS read-only
    STATUS current
    DESCRIPTION "<Definition> The tick count representing the most likely future time point when the signalState is expected to change, excluding unexpected events such as a preempt request. The value of this object will remain constant if the predicted future time point of the event does not change. Values from 0 to 35999 cover one hour. Values from 36000 to 36009 are used when a leap second occurs. Values from 36010 to 36110 are reserved for future use. A value of 36111 indicates the time point of the event is undefined or unknown.

This object is used with the ascCurrentTick2 object. If signalStateLikelyEndTick2 is greater than ascCurrentTick2 then the end time is in the current hour. If signalStateLikelyEndTick2 is less than ascCurrentTick2 then the time is in the next hour.

See Annex F.3.3.6.4 for additional guidance.
    <Object Identifier> 1.3.6.1.4.1.1206.4.2.17.1.12.1.5
    <Object Type> S"
    REFERENCE "SAE J2735 DE_TimeMark"
    DEFVAL { 36111 }
    ::= { signalStatusEntry2 5 }

--5.20.4.6  SPaT Signal State Time Confidence
signalStateTickConfidence2 OBJECT-TYPE
    SYNTAX Integer32 (0..15)
    MAX-ACCESS read-only
    STATUS current
    DESCRIPTION "<Definition> For NTCIP 1202 user clarification, the statistical confidence in the predicted value of the signalStateLikelyEndTick2.

See Annex F.3.3.6.5 for additional guidance.
    <Object Identifier> 1.3.6.1.4.1.1206.4.2.17.1.12.1.6
    <Object Type> S"
    REFERENCE "SAE J2735 DE_TimeIntervalConfidence"
    DEFVAL { 0 }
    ::= { signalStatusEntry2 6 }

--5.20.4.7  SPaT Signal Next Tick
signalStateNextTick2 OBJECT-TYPE
    SYNTAX Integer32 (0..36111)
    UNITS "tick"
    MAX-ACCESS read-only
    STATUS current
    DESCRIPTION "<Definition> The tick count representing the most likely future time point when the movement is expected to be allowed to move again (e.g., green), excluding unexpected events such as a preempt request. The value of this object will remain constant if the predicted future time point of the event does not change. Values from 0 to 35999 cover one hour. Values from 36000 to 36009 are used when a leap second occurs. Values from 36010 to 36110 are reserved for future use. A value of 36111 indicates the time point of the event is undefined or unknown.

This object is used with the ascCurrentTick2 object. If signalStateNextTick2 is greater than ascCurrentTick2 then the next time is in the current hour. If signalStateNextTick2 is less than ascCurrentTick2 then the time is in the next hour.

See Annex F.3.3.6.6 for additional guidance.
    <Object Identifier> 1.3.6.1.4.1.1206.4.2.17.1.12.1.7
    <Object Type> S"
    REFERENCE "SAE J2735 DE_TimeMark"
    DEFVAL { 36111 }
    ::= { signalStatusEntry2 7 }

--5.20.4.8  SPaT Signal Start Tick 
signalStateStartTick OBJECT-TYPE
    SYNTAX Integer32 (0..36111)
    UNITS "tick"
    MAX-ACCESS read-only
    STATUS current
    DESCRIPTION "<Definition> The tick count representing the start time of the next (future) movement state to follow the current movement state for a signal group. The value of this object will remain constant if the predicted future time point of the event does not change. Values from 0 to 35999 cover one hour. Values from 36000 to 36009 are used when a leap second occurs. Values from 36010 to 36110 are reserved for future use. A value of 36111 indicates the time point of the event is undefined or unknown.

This object is used with the ascCurrentTick2 object. If signalStateStartTick is greater than ascCurrentTick2 then the start time of the next movement state is in the current hour. If signalStateStartTick is less than ascCurrentTick2 then the time is in the next hour.

See Annex F.3.3.6.7 for additional guidance.
    <Object Identifier> 1.3.6.1.4.1.1206.4.2.17.1.12.1.8
    <Object Type> S"
    REFERENCE "SAE J2735 DE_TimeMark"
    DEFVAL { 36111 }
    ::= { signalStatusEntry2 8 }

--5.20.5   Maximum SPaT Speed Advisories
maxAdvisorySpeeds2 OBJECT-TYPE
    SYNTAX Integer32 (1..255)
    UNITS "advisory"
    MAX-ACCESS read-only
    STATUS current
    DESCRIPTION "<Definition> This object contains the maximum number of movement speed advisory entries this CU supports. This object indicates the maximum rows which shall appear in the advisorySpeedTable2 object.
    <Object Identifier> 1.3.6.1.4.1.1206.4.2.17.1.13
    <Object Type> S"
    ::= { spat 13 }

--5.20.6   SPaT Speed Advisories Table
advisorySpeedTable2 OBJECT-TYPE
    SYNTAX SEQUENCE OF AdvisorySpeedEntry2 
    MAX-ACCESS not-accessible
    STATUS current
    DESCRIPTION "<Definition> This table contains speed advisories for signalized intersections controlled by this CU. The number of rows in this table is equal to the maxAdvisorySpeeds2 object.
    <TableType> static
    <Object Identifier> 1.3.6.1.4.1.1206.4.2.17.1.14"
    ::= { spat 14 }

advisorySpeedEntry2 OBJECT-TYPE
    SYNTAX AdvisorySpeedEntry2
    MAX-ACCESS not-accessible
    STATUS current
    DESCRIPTION "<Definition> Speed advisory information for a signal group.
    <Object Identifier> 1.3.6.1.4.1.1206.4.2.17.1.14.1"
    INDEX  { advisorySpeedIndex2 }
    ::= { advisorySpeedTable2 1 }

AdvisorySpeedEntry2 ::= SEQUENCE {
    advisorySpeedIndex2                 Integer32,
    advisorySpeedSignalGroupEntryNumber Integer32,
    advisorySpeedType2                  INTEGER,
    advisorySpeedAdvice2                Integer32,
    advisorySpeedZoneLength2            Integer32,
    advisorySpeedClass2                 Integer32  }

--5.20.6.1  SPaT Speed Advisory Index
advisorySpeedIndex2 OBJECT-TYPE
    SYNTAX Integer32 (1..255)
    UNITS "number"
    MAX-ACCESS not-accessible
    STATUS current
    DESCRIPTION "<Definition> The advisory speed index for objects in this row. This value shall not exceed the maxAdvisorySpeeds2 object value.
    <Object Identifier> 1.3.6.1.4.1.1206.4.2.17.1.14.1.1"
    ::= { advisorySpeedEntry2 1 }

--5.20.6.2  SPaT Advisory Signal Group
advisorySpeedSignalGroupEntryNumber OBJECT-TYPE
    SYNTAX Integer32 (1..255)
    MAX-ACCESS read-write
    STATUS current
    DESCRIPTION "<Definition> The signalGroupEntryNumber that the speed advisory is applicable for. A value of zero indicates that the row is disabled and all other values in the row are not valid.
    <Object Identifier> 1.3.6.1.4.1.1206.4.2.17.1.14.1.2
    <Object Type> P"
    ::= { advisorySpeedEntry2 2 }

--5.20.6.3  SPaT Movement Advisory Speed Type
advisorySpeedType2 OBJECT-TYPE
    SYNTAX INTEGER { none (1),
                 greenwave (2),
                 ecoDrive (3),
                 transit (4) }
    MAX-ACCESS read-write
    STATUS current
    DESCRIPTION "<Definition> The type of speed advisory provided for this movement, such as greenwave or ecoDrive. Note: The enumerations do not match DE_AdvisorySpeedType.
    <Object Identifier> 1.3.6.1.4.1.1206.4.2.17.1.14.1.3
    <Object Type> P"
    REFERENCE "SAE J2735 DE_AdvisorySpeedType"
    DEFVAL { 1 }
    ::= { advisorySpeedEntry2 3 }

--5.20.6.4  SPaT Movement Advisory Speed Advice
advisorySpeedAdvice2 OBJECT-TYPE
    SYNTAX Integer32 (0..500)
    UNITS "decimeter per second"
    MAX-ACCESS read-write
    STATUS current
    DESCRIPTION "<Definition> The advisory speed provided by the ASC for this movement, in units of 0.1 meters per second. A value of 500 indicates that speed is unavailable.
    <Object Identifier> 1.3.6.1.4.1.1206.4.2.17.1.14.1.4
    <Object Type> P"
    REFERENCE "SAE J2735 DE_SpeedAdvice"
    DEFVAL { 500 }
    ::= { advisorySpeedEntry2 4 }

--5.20.6.5  SPaT Movement Advisory Speed Zone
advisorySpeedZoneLength2 OBJECT-TYPE
    SYNTAX Integer32 (0..10000)
    UNITS "meter"
    MAX-ACCESS read-write
    STATUS current
    DESCRIPTION "<Definition> The distance, in meters, indicates the region
        upstream from the stopbar for which the advisory speed is recommended.
        A value of zero indicates unknown. A value of 10000 indicates distances equal to or greater than 10000 meters.
    <Object Identifier> 1.3.6.1.4.1.1206.4.2.17.1.14.1.5
    <Object Type> P"
    REFERENCE "SAE J2735 DE_ZoneLength"
    ::= { advisorySpeedEntry2 5 }

--5.20.6.6  SPaT Movement Advisory Speed Restriction Class
advisorySpeedClass2 OBJECT-TYPE
    SYNTAX Integer32 (0..255)
    MAX-ACCESS read-write
    STATUS current
    DESCRIPTION "<Definition> The vehicle type(s) to which the advisory speed
        applies to. The value is provided in the MAP message for the
        intersection. A value of zero indicates that advisory speed applies to
        all vehicle types.
    <Object Identifier> 1.3.6.1.4.1.1206.4.2.17.1.14.1.6
    <Object Type> P"
    REFERENCE "SAE J2735 DE_RestrictionClassID"
    DEFVAL { 0 }
    ::= { advisorySpeedEntry2 6 }

--5.20.7    Maximum SPaT Movement Maneuvers
maxMovementManeuvers2 OBJECT-TYPE
    SYNTAX Integer32 (1..255)
    UNITS "maneuver"
    MAX-ACCESS read-only
    STATUS current
    DESCRIPTION "<Definition> This object contains the maximum number of rows which shall appear in the movementManeuverTable2 object.
    <Object Identifier> 1.3.6.1.4.1.1206.4.2.17.1.15
    <Object Type> S"
    ::= { spat 15 }

--5.20.8    SPaT Movement Maneuvers Table
movementManeuverTable2 OBJECT-TYPE
    SYNTAX SEQUENCE OF MovementManeuverEntry2 
    MAX-ACCESS not-accessible
    STATUS current
    DESCRIPTION "<Definition> This table contains information relevant to a maneuver that is related to a signal group at a signalized intersection. The number of rows in this table is equal to the maxMovementManeuvers2 object.
    <TableType> static
    <Object Identifier> 1.3.6.1.4.1.1206.4.2.17.1.16"
    ::= { spat 16 }

movementManeuverEntry2 OBJECT-TYPE
    SYNTAX MovementManeuverEntry2
    MAX-ACCESS not-accessible
    STATUS current
    DESCRIPTION "<Definition> Maneuvers information for a specific movement at a signalized intersection.
    <Object Identifier> 1.3.6.1.4.1.1206.4.2.17.1.16.1"
    INDEX  { movementManeuverIndex2 }
    ::= { movementManeuverTable2 1 }

MovementManeuverEntry2 ::= SEQUENCE {
    movementManeuverIndex2                 Integer32,
    movementManeuverSignalGroupEntryNumber Integer32,
    movementManeuverQueue2                 Integer32,
    movementManeuverStatus2                Integer32,
    movementManeuverQueueDetector2         OCTET STRING,
    movementManeuverPedPresence2           OCTET STRING,
    movementManeuverBicyclePresence2       OCTET STRING }

--5.20.8.1  SPaT Movement Maneuver Number
movementManeuverIndex2 OBJECT-TYPE
    SYNTAX Integer32 (1..255)
    MAX-ACCESS not-accessible
    STATUS current
    DESCRIPTION "<Definition> The movement maneuver index for objects in this row. This value shall not exceed the maxMovementManeuvers2 object value.
    <Object Identifier> 1.3.6.1.4.1.1206.4.2.17.1.16.1.1"
    ::= { movementManeuverEntry2 1 }

--5.20.8.2  SPaT Movement Maneuver Signal Group
movementManeuverSignalGroupEntryNumber OBJECT-TYPE
    SYNTAX Integer32 (0..255)
    MAX-ACCESS read-write
    STATUS current
    DESCRIPTION "<Definition> The signalGroupEntryNumber that the movement maneuver is applicable for. A value of zero indicates that the row is disabled and all other values in the row are not valid.
    <Object Identifier> 1.3.6.1.4.1.1206.4.2.17.1.16.1.2
    <Object Type> P"
    REFERENCE "SAE J2735 DE_SignalGroupID"
    ::= { movementManeuverEntry2 2 }

--5.20.8.3  SPaT Movement Queue
movementManeuverQueue2 OBJECT-TYPE
    SYNTAX Integer32 (0..10000)
    UNITS "meter"
    MAX-ACCESS read-only
    STATUS current
    DESCRIPTION "<Definition> The distance in meters from the stop line at the
        intersection for this movement to the back edge of the last vehicle in
        the queue as measured along the center line of the lane. A value of zero
        indicates no queue or the queue distance is unknown. A value of 10000
        represents all distance greater or equal to 10000 meters.
    <Object Identifier> 1.3.6.1.4.1.1206.4.2.17.1.16.1.3
    <Object Type> P"
    REFERENCE "SAE J2735 DF_ConnectionManeuverAssist and DE_ZoneLength"
    DEFVAL { 0 }
    ::= { movementManeuverEntry2 3 }

--5.20.8.4  SPaT Movement Assist Status
movementManeuverStatus2 OBJECT-TYPE
    SYNTAX Integer32 (0..255)
    MAX-ACCESS read-only
    STATUS current
    DESCRIPTION "<Definition> For NTCIP 1202 user clarification, this object defines the options for traveler connections through an intersection.
    Bit 7:  Reserved
    Bit 6:  Reserved
    Bit 5:  Reserved
    Bit 4:  Reserved
    Bit 3:  Reserved
    Bit 2:  Reserved
    Bit 1:  Vulnerable Road User -Status bit set to TRUE (1) if ANY pedestrians or bicyclists are detected in a conflicting movement. Set to FALSE (0) if there is a high certainty no pedestrians or bicyclists are present. The detectors providing this information is defined by movementManeuverPedPresence2 and movementManeuverBicyclePresence2
    Bit 0:  Reserved
    <Object Identifier> 1.3.6.1.4.1.1206.4.2.17.1.16.1.4
    <Object Type> P"
    REFERENCE "SAE J2735 DE_PedestrianBicycleDetect"
    ::= { movementManeuverEntry2 4 }

--5.20.8.5  SPaT Movement Queue Detector
movementManeuverQueueDetector2 OBJECT-TYPE
    SYNTAX OCTET STRING
    MAX-ACCESS read-write
    STATUS current
    DESCRIPTION "<Definition> Each octet in this octet string represents a vehicle detector number (vehicleDetectorNumber) in the vehicleDetectorTable that provides the data to determine movementManeuverQueue2. A value of zero0 indicates that no additional vehicle detectors follow in the octet string.
    Each octet cannot exceed the value of maxVehicleDetectors. 
    <Object Identifier> 1.3.6.1.4.1.1206.4.2.17.1.16.1.5
    <Object Type> P"
    ::= { movementManeuverEntry2 5 }

--5.20.8.6  SPaT Movement Pedestrian Presence
movementManeuverPedPresence2 OBJECT-TYPE
    SYNTAX OCTET STRING
    MAX-ACCESS read-write
    STATUS current
    DESCRIPTION "<Definition> Each octet in this octet string represents a pedestrian detector number (pedestrianDetectorNumber) in the pedestrianDetectorTable (with Bit 0 in the corresponding pedestrianDetectorOptions Enabled) whose detection status indicates a pedestrian is detected in the pedestrian crossing that conflicts with this movementManeuverSignalGroupEntryNumber. For example, an octet string of 01 03 indicates that if pedestrian detector 1 or pedestrian detector 3 is active/ON, then the presence of a pedestrian has been detected that conflicts with this movementManeuverSignalGroupEntryNumber. If a pedestrian is detected by any pedestrianDetectorNumber in the octet string, Bit 1 in movementManeuverStatus2 shall be SET to TRUE (1).
    <Object Identifier> 1.3.6.1.4.1.1206.4.2.17.1.16.1.6
    <Object Type> P"
    ::= { movementManeuverEntry2 6 }

--5.20.8.7  SPaT Movement Bicycle Presence
movementManeuverBicyclePresence2 OBJECT-TYPE
    SYNTAX OCTET STRING
    MAX-ACCESS read-write
    STATUS current
    DESCRIPTION "<Definition> Each octet in this octet string represents a vehicle detector number (vehicleDetectorNumber) in the vehicleDetectorTable that when active/ON indicates that a bicyclist is detected that conflicts with this movementManeuverSignalGroupEntryNumber. If a bicyclist is detected by any of the vehicleDetectorNumber in the octet string, Bit 1 in movementManeuverStatus2 shall be SET to TRUE (1). For example, an octet string of 02 06 indicates that if vehicle detector 2 or vehicle detector 6 is active/ON, then the presence of a bicyclist has been detected that conflicts with this movementManeuverSignalGroupEntryNumber.
    Each octet cannot exceed the value of maxVehicleDetectors. 
    <Object Identifier> 1.3.6.1.4.1.1206.4.2.17.1.16.1.7
    <Object Type> P"
    ::= { movementManeuverEntry2 7 }

--5.20.9    Road Authority Identifier
spatRoadAuthorityID OBJECT-TYPE
    SYNTAX OBJECT IDENTIFIER 
    MAX-ACCESS read-write
    STATUS current
    DESCRIPTION "<Definition> This object is the unique identifier of the agency for the SPaT and MAP message. This object shall be either a valid OBJECT IDENTIFIER or a null string. 
    <Object Identifier> 1.3.6.1.4.1.1206.4.2.17.1.17
    <Object Type> P"
    REFERENCE "SAE J2735 DE_RelativeRoadAuthorityID"
    DEFVAL { zeroDotZero }
    ::= { spat 17 }

--5.20.10    SPaT Signal Status Block
signalStatusBlock2 OBJECT-TYPE
    SYNTAX ITSOerString 
    MAX-ACCESS read-only
    STATUS current
    DESCRIPTION "<Definition> An OER encoded string of the signalStatusTable2
        structure as defined below. This object is used for uploading
        configuration data from the ASC in a bandwidth efficient manner.

        signalStatus2 ::= SEQUENCE {  
            ascCurrentTick2.0,       -- @NTCIP1202-v03B, Bytes 1 & 2
            spatStatus2.0            -- 2 BYTES @NTCIP1202-v03B
            spatEnabledLanesCount.0  -- 1 BYTE @NTCIP1202-v03B
            spatEnabledLanesStatus.0 -- n BYTES
            signalGroupEntryCount.0  -- 1 BYTE
            signalData2     SEQUENCE OF SignalStatusData2   OPTIONAL }

        SignalStatusData2 ::== SEQUENCE {
            signalGroupEntryNumber.y    -- 1 BYTE
            signalState2.y.x            -- 1 BYTE @NTCIP1202-v03B
            signalStateMinEndTick2.y.x  -- 2 BYTES @NTCIP1202-v03B
            signalStateMaxEndTick2.y.x  -- 2 BYTES @NTCIP1202-v03B
            signalStateNextTick2.y.x    -- 2 BYTES @NTCIP1202-v03B
            signalStateStartTick.y.x    -- 2 BYTES @NTCIP1202-v03B }

        where:
            n = spatEnabledLanesCount. This is the number of octets in the
                OCTET STRING of spatEnabledLanesStatus
            signalGroupEntryCount is a count of the number of
                signalGroupEntryNumber included in this object. Only
                signalGroupEntryNumbers that are active (in use) are to be
                included.
            y is the signalGroupEntryNumber in the signalGroupEntryTable
            x is the movementEventNumber for the signalStatusTable2. Only a
                value of 1 (current interval) and 2 (next interval) are used.

        For example, if (y = ) signalGroupEntryNumbers 1, 2, 4, 8, 13 and 16
            are included in this object, then signalGroupEntryCount.0 is equal
            to 6 and the SEQUENCE OF SignalStatusData2 is y = 1, 2, 4, 8, 13,
            and 16. x will still be 1, 2.

        Although this object theoretically allows up to 255
            signalGroupEntryNumbers, check that the number does not exceed the
            Maximum Transmission Unit (MTU) of the lower layers used.

        An example of signalStatusBlock2 is provided in Annex F.3.3.3.1.

        See Annex E.2 for the equivalent object definition for the RSU.
        Note: It is necessary that the signalGroupIntersection and
        signalGroupID objects be SET in the RSU before the signalStatusBlock2
        is SET to the RSU.

    <Object Identifier> 1.3.6.1.4.1.1206.4.2.17.1.18"
    ::= { spat 18 }

--7.3   MAP Data 
map OBJECT IDENTIFIER
    ::= { saeNtcip 2 }

-- This defines a node for supporting roadway geometry plan objects for a connected vehicle environment.

--7.3.1 MAP Message Count
mapMsgCount OBJECT-TYPE
    SYNTAX Integer32 (0..127)
    MAX-ACCESS read-only
    STATUS deprecated
    DESCRIPTION "<Definition> For NTCIP 1202 user clarification, a sequence number that is incremented when the contents of the MAP data message has changed. The value after 127 is 0.
    <Object Identifier> 1.3.6.1.4.1.1206.4.2.17.2.1"
    REFERENCE "SAE J2735 DE_MsgCount"
    ::= { map 1 }

--7.3.2 MAP Message Time
mapMessageTime OBJECT-TYPE
    SYNTAX Integer32 (0..527040)
    MAX-ACCESS read-write
    STATUS deprecated
    DESCRIPTION "<Definition> For NTCIP 1202 user clarification, this object indicates the minute of the year the MAP data message was last created by the RSU.
    <Object Identifier> 1.3.6.1.4.1.1206.4.2.17.2.2"
    REFERENCE "SAE J2735 DE_MinuteOfTheYear"
    DEFVAL  { 0 }
    ::= { map 2 }

--7.3.3 Maximum Number of Lanes
maxLanes OBJECT-TYPE
    SYNTAX Integer32 (1..255)
    UNITS "lane"
    MAX-ACCESS read-only
    STATUS deprecated
    DESCRIPTION "<Definition> This object contains the maximum number of lane entries this CU supports. This object indicates the maximum rows which shall appear in the mapLaneTable object.
    <Object Identifier> 1.3.6.1.4.1.1206.4.2.17.2.3
    <Object Type> S"
    ::= { map 3 }

--7.3.4 Intersection Lane Table
mapLaneTable OBJECT-TYPE
    SYNTAX SEQUENCE OF MapLaneEntry 
    MAX-ACCESS not-accessible
    STATUS deprecated
    DESCRIPTION "<Definition> This table contains lane information for intersections. The number of rows in this table is equal to the maxLanes object.
    <TableType> static
    <Object Identifier> 1.3.6.1.4.1.1206.4.2.17.2.4"
    ::= { map 4 }

mapLaneEntry OBJECT-TYPE
    SYNTAX MapLaneEntry
    MAX-ACCESS not-accessible
    STATUS deprecated
    DESCRIPTION "<Definition> The parameters for a specific lane at an intersection.
    <Object Identifier> 1.3.6.1.4.1.1206.4.2.17.2.4.1"
    INDEX  { mapLaneIndex }
    ::= { mapLaneTable 1 }

MapLaneEntry::= SEQUENCE {
    mapLaneIndex        INTEGER,        --deprecated
    mapLaneIntersection INTEGER,        --deprecated
    mapLaneNumber       INTEGER,        --deprecated
    mapLaneName         DisplayString,  --deprecated
    mapLaneDirection    INTEGER,        --deprecated
    mapLaneSharing      INTEGER,        --deprecated
    mapLaneType         INTEGER,        --deprecated
    mapLaneAttribute    INTEGER,        --deprecated
    mapLaneManeuver     INTEGER,        --deprecated
    mapLaneOverlay      OCTET STRING,   --deprecated
    mapLaneIngress      INTEGER,        --deprecated
    mapLaneEgress       INTEGER,        --deprecated
    mapLaneCRC          OCTET STRING }  --deprecated

--7.3.4.1   Lane Index
mapLaneIndex OBJECT-TYPE
    SYNTAX Integer32 (1..255)
    UNITS "lane"
    MAX-ACCESS not-accessible
    STATUS deprecated
    DESCRIPTION "<Definition> The lane index of objects in this row. The entries in each row define the attributes of a specific lane (mapLaneNumber) at a referenced intersection (mapLaneIntersection). This value shall not exceed the maxLanes object value.
    <Object Identifier> 1.3.6.1.4.1.1206.4.2.17.2.4.1.1"
    ::= { mapLaneEntry 1 }

--7.3.4.2   Lane Intersection
mapLaneIntersection OBJECT-TYPE
    SYNTAX Integer32 (1..255)
    UNITS "lane"
    MAX-ACCESS read-write
    STATUS deprecated
    DESCRIPTION "<Definition> The index of the intersection (mapIntersectionIndex) that this lane is associated with.
    <Object Identifier> 1.3.6.1.4.1.1206.4.2.17.2.4.1.2"    
    ::= { mapLaneEntry 2 }

--7.3.4.3   Lane Number
mapLaneNumber OBJECT-TYPE
    SYNTAX Integer32 (1..255)
    MAX-ACCESS read-only
    STATUS deprecated
    DESCRIPTION "<Definition> For NTCIP 1202 user clarification, the identifier of the lane of the referenced intersection (mapLaneIntersection).
    <Object Identifier> 1.3.6.1.4.1.1206.4.2.17.2.4.1.3"
    REFERENCE "SAE J2735 DF_GenericLane and DE_LaneID"
    ::= { mapLaneEntry 3 }

--7.3.4.4   Lane Name
mapLaneName OBJECT-TYPE
    SYNTAX DisplayString (SIZE (1..63)) 
    MAX-ACCESS read-write 
    STATUS deprecated 
    DESCRIPTION "<Definition> For NTCIP 1202 user clarification, a textual string describing the lane.
    <Object Identifier> 1.3.6.1.4.1.1206.4.2.17.2.4.1.4"
    REFERENCE "SAE J2735 DF_GenericLane and DE_DescriptiveName"
    ::= { mapLaneEntry 4 }

--7.3.4.5   Lane Direction
mapLaneDirection OBJECT-TYPE
    SYNTAX Integer32 (0..3)
    MAX-ACCESS read-write
    STATUS deprecated
    DESCRIPTION "<Definition> For NTCIP 1202 user clarification, this object denotes the allowed direction of travel over the lane.
    <Object Identifier> 1.3.6.1.4.1.1206.4.2.17.2.4.1.5"
    REFERENCE "SAE J2735 DE_LaneDirection"
    DEFVAL { 0 }
    ::= { mapLaneEntry 5 }

--7.3.4.6   Lane Sharing
mapLaneSharing OBJECT-TYPE
    SYNTAX Integer32 (0..1023)
    MAX-ACCESS read-write
    STATUS deprecated
    DESCRIPTION "<Definition> For NTCIP 1202 user clarification, this object describes other users (travel modes) with equal rights and access to the lane.
    <Object Identifier> 1.3.6.1.4.1.1206.4.2.17.2.4.1.6"
    REFERENCE "SAE J2735 DE_LaneSharing"
    DEFVAL { 0 }
    ::= { mapLaneEntry 6 }

--7.3.4.7   Lane Type
mapLaneType OBJECT-TYPE
    SYNTAX INTEGER { vehicle (0), -- motor vehicle lanes
                 crosswalk (1),  -- pedestrian crosswalk
                 bikelane (2),   -- bike lane
                 sidewalk (3),   -- pedestrian sidewalk path
                 median (4),     -- median and channelization
                 striping (5),   -- roadway marking
                 trackedvehicle (6), -- trains, trolleys, light rail
                 parking (7) }   -- parking or stopping lane
    MAX-ACCESS read-write
    STATUS deprecated
    DESCRIPTION "<Definition> For NTCIP 1202 user clarification, this object defines the type of lane. This value is used to determine the meaning of the values in mapLaneAttribute.
    <Object Identifier> 1.3.6.1.4.1.1206.4.2.17.2.4.1.7" 
    REFERENCE "SAE J2735 DF_LaneTypeAttributes"
    DEFVAL { vehicle }
    ::= { mapLaneEntry 7 }

--7.3.4.8   Lane Attribute
mapLaneAttribute OBJECT-TYPE
    SYNTAX Integer32 (0..65535)
    MAX-ACCESS read-write
    STATUS deprecated
    DESCRIPTION "<Definition> For NTCIP 1202 user clarification, if a specific attribute for the lane is true, the associated bit shall be set to (1). Bit 0 is equal to Bit 0 of the BIT STRING of the appropriate LaneAttribute type, Bit 1 is equal to Bit 1, etc. If the mapLaneType is vehicle (0), then the attribute values are defined by SAE J2735 DE_LaneAttributes-Vehicle.
If the mapLaneType is crosswalk (1), then the attribute values are defined by SAE J2735 DE_LaneAttributes-Crosswalk. 
If the mapLaneType is bikelane (2), then the attribute values are defined by SAE J2735 DE_LaneAttributes-Bike.
If the mapLaneType is sidewalk (3), then the attribute values are defined by SAE J2735 DE_LaneAttributes-Sidewalk.
If the mapLaneType is median (4), then the attribute values are defined by SAE J2735 DE_LaneAttributes-Barrier.
If the mapLaneType is striping (5), then the attribute values are defined by SAE J2735 DE_LaneAttributes-Striping.
If the mapLaneType is trackedvehicle(6), then the attribute values are defined by SAE J2735 DE_LaneAttributes-TrackedVehicle.
If the mapLaneType is parking (7), then the attribute values are defined by SAE J2735 DE_LaneAttributes-ParkingLane.
Note: Bit 0 should not be enabled as a revocable lane for mapLaneIndex = 255. It is reserved for spatEnabledLanesCommand.

    <Object Identifier> 1.3.6.1.4.1.1206.4.2.17.2.4.1.8"
    REFERENCE "SAE J2735 DF_LaneTypeAttributes"
    ::= { mapLaneEntry 8 }

--7.3.4.9   Lane Maneuver
mapLaneManeuver OBJECT-TYPE
    SYNTAX Integer32 (0..4095)
    MAX-ACCESS read-write
    STATUS deprecated
    DESCRIPTION "<Definition> For NTCIP 1202 user clarification, represents the allowed maneuvers from this lane at the stop line. Note: these values may be further restricted by vehicle class, local regulations or other changing conditions.
    <Object Identifier> 1.3.6.1.4.1.1206.4.2.17.2.4.1.9"
    REFERENCE "SAE J2735 DE_AllowedManeuvers"
    ::= { mapLaneEntry 9 }

--7.3.4.10  Lane Overlay
mapLaneOverlay OBJECT-TYPE
    SYNTAX OCTET STRING
    MAX-ACCESS read-write 
    STATUS deprecated
    DESCRIPTION "<Definition> For NTCIP 1202 user clarification, each octet in this octet string represents the index of the lanes (mapLaneIndex) that overlay (run on top of) the spatial path of this lane. If there is no overlay lane, the octet shall be set to 00.
    <Object Identifier> 1.3.6.1.4.1.1206.4.2.17.2.4.1.10" 
    REFERENCE "SAE J2735 DF_OverlayLaneList"
    ::= { mapLaneEntry 10 }

--7.3.4.11  Lane Ingress
mapLaneIngress OBJECT-TYPE
    SYNTAX Integer32 (0..15)
    MAX-ACCESS read-write 
    STATUS deprecated 
    DESCRIPTION "<Definition> For NTCIP 1202 user clarification, an index of an approach, to aid in the gross position of a traveler. Intended when the MAP data represents lanes as a group of lanes and not as individual lanes.
    <Object Identifier> 1.3.6.1.4.1.1206.4.2.17.2.4.1.11"
    REFERENCE "SAE J2735 DF_GenericLane and DE_ApproachID"
    DEFVAL { 0 }
    ::= { mapLaneEntry 11 }

--7.3.4.12  Lane Egress
mapLaneEgress OBJECT-TYPE
    SYNTAX Integer32 (0..15)
    MAX-ACCESS read-write
    STATUS deprecated
    DESCRIPTION "<Definition> For NTCIP 1202 user clarification, an index of an approach, to aid in the gross position of a traveler. Intended when the MAP data represents lanes as a group of lanes and not as individual lanes.
    <Object Identifier> 1.3.6.1.4.1.1206.4.2.17.2.4.1.12" 
    REFERENCE "SAE J2735 DF_GenericLane and DE_ApproachID"
    DEFVAL { 0 }
    ::= { mapLaneEntry 12 }

--7.3.4.13  MAP Lane CRC
mapLaneCRC OBJECT-TYPE
    SYNTAX OCTET STRING (SIZE(2))
    MAX-ACCESS read-only
    STATUS deprecated
    DESCRIPTION "<Definition> The mapLaneCRC is the CRC-16 (polynomial defined
        in ISO/IEC 13239:2002) of the associated OER-encoded (as defined in
        NTCIP 1102) MapLaneCRCByteStream.
 
        MapLaneCRCByteStream ::= SEQUENCE {
            mapLaneIntersection.x    INTEGER(1..255),
            mapLaneNumber.x          INTEGER(0..255),
            mapLaneDirection.x       BITSTRING(SIZE(2)),
            mapLaneSharing.x         BITSTRING(SIZE(10)),    
            mapLaneType.x            INTEGER(0..255),
            mapLaneAttribute.x       BITSTRING(SIZE(16)),
            mapLaneManeuver.x        BITSTRING(SIZE(12)),
            mapNodePointX.x.1        INTEGER(-179999999..180000001),
            mapNodePointY.x.1        INTEGER(-90000000..90000001),
            mapComputedLaneXOffset.1 INTEGER(-32767..32767),
            mapComputedLaneYOffset.1 INTEGER(-32767..32767) }

        Only the first node point of a lane is included in the construct. It
        is assumed that if all the other characteristics of the lane did not
        change, and the first node point of the lane remains the same, it is
        likely the lane path did not change. Note that one of the
        mapNodePointX.x.1/mapNodePointY.x.1 pair or 
        mapComputedLaneXOffset.x.1/mapComputedLaneYOffset.x.1 pair will have
        A value of zero0 00.
    <Object Identifier> 1.3.6.1.4.1.1206.4.2.17.2.4.1.13" 
    ::= { mapLaneEntry 13 }

--7.3.5 Maximum Number of Intersections
maxMapIntersections OBJECT-TYPE
    SYNTAX Integer32 (1..64) -- no requirement to GET this object individually 
    UNITS "intersection"
    MAX-ACCESS read-only
    STATUS deprecated
    DESCRIPTION "<Definition> This object contains the maximum number of intersection entries this CU supports. Each entry represents an intersection that may be included in the MAP data stored and broadcasted by a RSU. This object indicates the maximum rows which shall appear in the mapIntersectionTable object.
    <Object Identifier> 1.3.6.1.4.1.1206.4.2.17.2.5"
    ::= { map 5 }

--7.3.6 MAP Intersection Table
mapIntersectionTable OBJECT-TYPE
    SYNTAX SEQUENCE OF MapIntersectionEntry 
    MAX-ACCESS not-accessible
    STATUS deprecated
    DESCRIPTION "<Definition> This table contains information describing an intersection that may be included in a MAP message, including its reference point. The number of rows in this table is equal to the maxMapIntersections object.
    <TableType> static
    <Object Identifier> 1.3.6.1.4.1.1206.4.2.17.2.6"
    ::= { map 6 }

mapIntersectionEntry OBJECT-TYPE
    SYNTAX MapIntersectionEntry
    MAX-ACCESS not-accessible
    STATUS deprecated
    DESCRIPTION "<Definition> Description and characteristics of an
        intersection that may be broadcast in a MAP message.
    <Object Identifier> 1.3.6.1.4.1.1206.4.2.17.2.6.1"
    INDEX  { mapIntersectionIndex }
    ::= { mapIntersectionTable 1 }

MapIntersectionEntry::= SEQUENCE {
    mapIntersectionIndex        INTEGER,
    mapIntersectionId           INTEGER,
    mapIntersectionName         DisplayString,
    mapIntersectionAuthority    INTEGER,
    mapIntersectionLatitude     INTEGER, --deprecated
    mapIntersectionLongitude    INTEGER, --deprecated
    mapIntersectionElevation    INTEGER, --deprecated
    mapIntersectionDefaultWidth INTEGER, --deprecated
    mapIntersectionMsgCount     INTEGER } --deprecated

--7.3.6.1   MAP Intersection Index
mapIntersectionIndex OBJECT-TYPE
    SYNTAX Integer32 (1..64)
    UNITS "node"
    MAX-ACCESS not-accessible
    STATUS deprecated
    DESCRIPTION "<Definition> The index number of the intersection objects in this row. This value shall not exceed the maxMapIntersections object value.
    <Object Identifier> 1.3.6.1.4.1.1206.4.2.17.2.6.1.1
    <Object Type> S"
    ::= { mapIntersectionEntry 1 }

--7.3.6.2   MAP Intersection Identifier
mapIntersectionId OBJECT-TYPE
    SYNTAX Integer32 (1..65535)
    MAX-ACCESS read-write
    STATUS deprecated
    DESCRIPTION "<Definition> For NTCIP 1202 user clarification, an identifier to uniquely define an intersection within a region.
    <Object Identifier> 1.3.6.1.4.1.1206.4.2.17.2.6.1.2
    <Object Type> P"
    REFERENCE "SAE J2735 DE_IntersectionID"
    ::= { mapIntersectionEntry 2 }

--7.3.6.3   MAP Intersection Name
mapIntersectionName OBJECT-TYPE
    SYNTAX DisplayString (SIZE (1..63))
    MAX-ACCESS read-write
    STATUS deprecated
    DESCRIPTION "<Definition> For NTCIP 1202 user clarification, an textual string describing the intersection.
    <Object Identifier> 1.3.6.1.4.1.1206.4.2.17.2.6.1.3"
    REFERENCE "SAE J2735 DE_DescriptiveName
    <Object Type> P"
    ::= { mapIntersectionEntry 3 }

--7.3.6.4   MAP Authority Identifier
mapIntersectionAuthority OBJECT-TYPE
    SYNTAX Integer32 (0..65535)
    MAX-ACCESS read-write
    STATUS deprecated
    DESCRIPTION "<Definition> For NTCIP 1202 user clarification, a globally unique identifier assigned to an entity in a region (or country) responsible for assigning the intersectionId. The value 0 is reserved for testing and is SET only in the absence of a suitable assignment.
    <Object Identifier> 1.3.6.1.4.1.1206.4.2.17.2.6.1.4
    <Object Type> P"
    REFERENCE "SAE J2735 DE_RoadRegulatorID"
    ::= { mapIntersectionEntry 4 }

--7.3.6.5   MAP Intersection Latitude
mapIntersectionLatitude OBJECT-TYPE
    SYNTAX INTEGER (-90000000..90000001)
    MAX-ACCESS read-write
    STATUS deprecated
    DESCRIPTION "<Definition> For NTCIP 1202 user clarification, the latitude of the intersection's reference point.
    <Object Identifier> 1.3.6.1.4.1.1206.4.2.17.2.6.1.5"
    REFERENCE "SAE J2735 DE_Latitude"
    DEFVAL  { 90000001 }
    ::= { mapIntersectionEntry 5 }

--7.3.6.6   MAP Intersection Longitude
mapIntersectionLongitude OBJECT-TYPE
    SYNTAX INTEGER (-179999999..180000001)
    MAX-ACCESS read-write
    STATUS deprecated
    DESCRIPTION "<Definition> For NTCIP 1202 user clarification, the geographic longitude of the intersection's reference point.
    <Object Identifier> 1.3.6.1.4.1.1206.4.2.17.2.6.1.6"
    REFERENCE "SAE J2735 DE_Longitude"
    DEFVAL  { 180000001 }
    ::= { mapIntersectionEntry 6 }

--7.3.6.7   MAP Intersection Elevation
mapIntersectionElevation OBJECT-TYPE
    SYNTAX INTEGER (-4096..61439)
    MAX-ACCESS read-write
    STATUS deprecated
    DESCRIPTION "<Definition> For NTCIP 1202 user clarification, the elevation of the intersection's reference point.
    <Object Identifier> 1.3.6.1.4.1.1206.4.2.17.2.6.1.7"
    REFERENCE "SAE J2735 DE_Elevation"
    DEFVAL { -4096 }
    ::= { mapIntersectionEntry 7 }

--7.3.6.8   MAP Intersection Default Width
mapIntersectionDefaultWidth OBJECT-TYPE
    SYNTAX Integer32 (0..32767)
    MAX-ACCESS read-write
    STATUS deprecated
    DESCRIPTION "<Definition> For NTCIP 1202 user clarification, the default lane width for the intersection.
    <Object Identifier> 1.3.6.1.4.1.1206.4.2.17.2.6.1.8"
    REFERENCE "SAE J2735 DE_LaneWidth"
    DEFVAL { 0 }
    ::= { mapIntersectionEntry 8 }

--7.3.6.9   MAP Intersection Message Count
mapIntersectionMsgCount OBJECT-TYPE
    SYNTAX Integer32 (0..127)
    MAX-ACCESS read-only
    STATUS deprecated
    DESCRIPTION "<Definition> For NTCIP 1202 user clarification, a sequence number that is incremented when the contents for the intersection in the MAP data message has changed.
    <Object Identifier> 1.3.6.1.4.1.1206.4.2.17.2.6.1.9"
    REFERENCE "SAE J2735 DF_IntersectionGeometry and DE_MsgCount"
    ::= { mapIntersectionEntry 9 }

--7.3.7 Maximum Number of Node Points
maxNodePoints OBJECT-TYPE
    SYNTAX INTEGER (2..63)
    UNITS "node"
    MAX-ACCESS read-only
    STATUS deprecated
    DESCRIPTION "<Definition> This object contains the maximum number of node point entries this CU supports. Each node point represents a point along the path of a lane. This object indicates the maximum rows which shall appear in the mapNodePointTable object.
    <Object Identifier> 1.3.6.1.4.1.1206.4.2.17.2.7"
    ::= { map 7 }

--7.3.8 Node Point Table
mapNodePointTable OBJECT-TYPE
    SYNTAX SEQUENCE OF MapPathEntry 
    MAX-ACCESS not-accessible
    STATUS deprecated
    DESCRIPTION "<Definition> This table contains node point information describing the path of a lane at an intersection. The number of rows in this table is equal to the maxNodePoints object.
    <TableType> static
    <Object Identifier> 1.3.6.1.4.1.1206.4.2.17.2.8"
    ::= { map 8 }

mapPathEntry OBJECT-TYPE
    SYNTAX MapPathEntry
    MAX-ACCESS not-accessible
    STATUS deprecated
    DESCRIPTION "<Definition> The node offsets for a specific lane at an intersection.
    <Object Identifier> 1.3.6.1.4.1.1206.4.2.17.2.8.1"
    INDEX  { mapLaneIndex, mapNodePointNumber }
    ::= { mapNodePointTable 1 }

MapPathEntry::= SEQUENCE {
    mapNodePointNumber      INTEGER, --deprecated
    mapNodePointX           INTEGER, --deprecated
    mapNodePointY           INTEGER, --deprecated
    mapNodePointAttribute   INTEGER, --deprecated
    mapNodeSegmentAttribute INTEGER, --deprecated
    mapNodePointEndAngle    INTEGER, --deprecated
    mapNodePointCrownCenter INTEGER, --deprecated
    mapNodePointCrownLeft   INTEGER, --deprecated
    mapNodePointCrownRight  INTEGER, --deprecated
    mapNodePointAngle       INTEGER, --deprecated
    mapNodePointWidth       INTEGER, --deprecated
    mapNodePointElevation   INTEGER, --deprecated
    mapNodePointSpeedLimits OCTET STRING } --deprecated

--7.3.8.1   Node Point Number
mapNodePointNumber OBJECT-TYPE
    SYNTAX Integer32 (1..255)
    UNITS "node"
    MAX-ACCESS not-accessible
    STATUS deprecated
    DESCRIPTION "<Definition> The node number of objects in this row. This value shall not exceed the maxNodePoints object value.
    <Object Identifier> 1.3.6.1.4.1.1206.4.2.17.2.8.1.1"
    ::= { mapPathEntry 1 }

--7.3.8.2   Node Point X
mapNodePointX OBJECT-TYPE
    SYNTAX INTEGER (-179999999..180000001)
    MAX-ACCESS read-write 
    STATUS deprecated 
    DESCRIPTION "<Definition> For NTCIP 1202 user clarification, represents the X offset from the previous node OR the geographic longitude position, as determined by Bit 15 in mapNodePointAttribute. If the value is an offset, the offset is measured from the previous path node (defined in the previous row of this table, with the first path node defined in the row mapNodePointNumber = 1), in centimeters. For row mapNodePointNumber = 1, the offset is from the intersection's reference point (intersectionLongitude). The sequence of nodes defines the centerline of the lane. A positive value is to the East.

    If this object is a geographic position, the value represents the geographic longitude of the path node. The value 1800000001 is unknown.
    <Object Identifier> 1.3.6.1.4.1.1206.4.2.17.2.8.1.2"
    REFERENCE "SAE J2735 DF_NodeOffsetPointXY"
    ::= { mapPathEntry 2 }

--7.3.8.3   Node Point Y
mapNodePointY OBJECT-TYPE
    SYNTAX INTEGER (-90000000..90000001)
    MAX-ACCESS read-write
    STATUS deprecated
    DESCRIPTION "<Definition> For NTCIP 1202 user clarification, represents the Y offset from the previous node OR the geographic latitude position, as determined by Bit 15 of the mapNodePointAttribute. If the value is an offset, the offset is measured from the previous path node (defined in the previous row of this table, with the first path node defined in the row mapNodePointNumber = 1), in centimeters. For row mapNodePointNumber = 1, the offset is from the intersection's reference point (intersectionLatitude). The sequence of nodes defines the centerline of the lane. A positive value is to the North.

    If this object is a geographic position, the value represents the geographic latitude of the path node. The value 900000001 is unknown.
    <Object Identifier> 1.3.6.1.4.1.1206.4.2.17.2.8.1.3"
    REFERENCE "SAE J2735 DF_NodeOffsetPointXY"
    ::= { mapPathEntry 3 }

--7.3.8.4   Node Point Attributes
mapNodePointAttribute OBJECT-TYPE
    SYNTAX Integer32 (0..65535)
    MAX-ACCESS read-write
    STATUS deprecated
    DESCRIPTION "<Definition> For NTCIP 1202 user clarification, defines the attributes that pertain to the current node point. If an attribute is TRUE, the associated bit shall be set to (1).
    <Object Identifier> 1.3.6.1.4.1.1206.4.2.17.2.8.1.4"
    REFERENCE "SAE J2735 DF_NodeAttributeXYList"
    ::= { mapPathEntry 4 }

--7.3.8.5   Node Point Segment Attributes
mapNodeSegmentAttribute OBJECT-TYPE
    SYNTAX Integer32 (0..65535)
    MAX-ACCESS read-write 
    STATUS deprecated 
    DESCRIPTION "<Definition> For NTCIP 1202 user clarification, defines the attributes about the current lane segment. A segment is one or more straight lines formed between each set of path nodes. If an attribute is TRUE, the associated bit shall be set to (1), and indicates that the attribute exists between this path node and the next path node (defined in the next row of the mapNodePointTable).
    <Object Identifier> 1.3.6.1.4.1.1206.4.2.17.2.8.1.5"
    REFERENCE "SAE J2735 DF_SegmentAttributeXYList"
    ::= { mapPathEntry 5 }

--7.3.8.6   Node Point End Angle
mapNodePointEndAngle OBJECT-TYPE
    SYNTAX INTEGER (-151..150)
    MAX-ACCESS read-write 
    STATUS deprecated 
    DESCRIPTION "<Definition> For NTCIP 1202 user clarification, provides the final angle used in the last point of the lane path. Used to 'cant' the stop line of the lane.
    <Object Identifier> 1.3.6.1.4.1.1206.4.2.17.2.8.1.6 "
    REFERENCE "SAE J2735 DE_DeltaAngle"
    DEFVAL { -151 }
    ::= { mapPathEntry 6 }

--7.3.8.7   Node Point Crown Point Center
mapNodePointCrownCenter OBJECT-TYPE
    SYNTAX INTEGER (-128..127)
    MAX-ACCESS read-write 
    STATUS deprecated 
    DESCRIPTION "<Definition> For NTCIP 1202 user clarification, relates the gross tangential angle of the roadway surface with respect to the local horizontal axis measured at the crown (centerline) of the lane at this node point.
    <Object Identifier> 1.3.6.1.4.1.1206.4.2.17.2.8.1.7"
    REFERENCE "SAE J2735 DE_RoadwayCrownAngle"
    DEFVAL { -128 }
    ::= { mapPathEntry 7 }

--7.3.8.8   Node Point Crown Point Left Edge
mapNodePointCrownLeft OBJECT-TYPE
    SYNTAX INTEGER (-128..127)
    MAX-ACCESS read-write
    STATUS deprecated
    DESCRIPTION "<Definition> For NTCIP 1202 user clarification, relates the gross tangential angle of the roadway surface with respect to the local horizontal axis measured at the left edge of the lane (in the normal direction of traffic) at this node point.
    <Object Identifier> 1.3.6.1.4.1.1206.4.2.17.2.8.1.8"
    REFERENCE "SAE J2735 DE_RoadwayCrownAngle"
    DEFVAL { -128 }
    ::= { mapPathEntry 8 }

--7.3.8.9   Node Point Crown Point Right Edge
mapNodePointCrownRight OBJECT-TYPE
    SYNTAX INTEGER (-128..127)
    MAX-ACCESS read-write
    STATUS deprecated
    DESCRIPTION "<Definition> For NTCIP 1202 user clarification, relates the gross tangential angle of the roadway surface with respect to the local horizontal axis measured at the right edge of the lane (in the normal direction of traffic) at this node point. The value 0 indicates an angle between -0.15 and +0.15 degrees. The value -128 shall be used for unknown. Note: SAE J2735 does not clearly define positive values.
    <Object Identifier> 1.3.6.1.4.1.1206.4.2.17.2.8.1.9"
    REFERENCE "SAE J2735 DE_RoadwayCrownAngle"
    DEFVAL { -128 }
    ::= { mapPathEntry 9 }

--7.3.8.10  Node Point Lane Angle
mapNodePointAngle OBJECT-TYPE
    SYNTAX INTEGER (-180..180)
    MAX-ACCESS read-write
    STATUS deprecated
    DESCRIPTION "<Definition> For NTCIP 1202 user clarification, provides the angle and direction at which another lane path meets the current lane at the node point.
    <Object Identifier> 1.3.6.1.4.1.1206.4.2.17.2.8.1.10"
    REFERENCE "SAE J2735 DE_MergeDivergeNodeAngle"
    DEFVAL { -180 }
    ::= { mapPathEntry 10 }

--7.3.8.11  Node Point Width
mapNodePointWidth OBJECT-TYPE
    SYNTAX INTEGER (-512..511)
    MAX-ACCESS read-write
    STATUS deprecated
    DESCRIPTION "<Definition> For NTCIP 1202 user clarification, a value added to the current lane width at this node and from this node onwards. Lane widths between nodes are a linear taper between points. Note: SAE J2735_1603 states that zero is not allowed.
    <Object Identifier> 1.3.6.1.4.1.1206.4.2.17.2.8.1.11"
    REFERENCE "SAE J2735 DF_NodeAttributeSetXY and DE_Offset_B10"
    ::= { mapPathEntry 11 }

--7.3.8.12  Node Point Elevation
mapNodePointElevation OBJECT-TYPE
    SYNTAX INTEGER (-512..511)
    MAX-ACCESS read-write
    STATUS deprecated
    DESCRIPTION "<Definition> For NTCIP 1202 user clarification, a value added to the current elevation at this node from this node onwards. Lane elevations between nodes are a linear taper between points. Note: SAE J2735_1603 states that zero is not allowed.
    <Object Identifier> 1.3.6.1.4.1.1206.4.2.17.2.8.1.12"
    REFERENCE "SAE J2735 DF_NodeAttributeSetXY and DE_Offset_B10"
    ::= { mapPathEntry 12 }

--7.3.8.13  Node Point Speed Limits
mapNodePointSpeedLimits OBJECT-TYPE
    SYNTAX OCTET STRING
    MAX-ACCESS read-write
    STATUS deprecated
    DESCRIPTION "<Definition> For NTCIP 1202 user clarification, each octet within the octet string contains a mapSpeedLimitIndex (binary value) that is applicable at this path node. The values of the mapSpeedLimitIndex shall not exceed mapSpeedLimits.
    <Object Identifier> 1.3.6.1.4.1.1206.4.2.17.2.8.1.13"
    REFERENCE "SAE J2735 DF_LaneDataAttribute and DF_RegulatorySpeedLimit"
    ::= { mapPathEntry 13 }

--7.3.9 Maximum Computed Lane
maxComputedLanes OBJECT-TYPE
    SYNTAX Integer32 (1..255)
    UNITS "lane"
    MAX-ACCESS read-only
    STATUS deprecated
    DESCRIPTION "<Definition> For NTCIP 1202 user clarification, this object contains the maximum number of computed lane entries this ASC supports. This object indicates the maximum rows which shall appear in the mapComputedLaneTable object.
    <Object Identifier> 1.3.6.1.4.1.1206.4.2.17.2.9"
    REFERENCE "SAE J2735 DF_ComputedLane"
    ::= { map 9 }

--7.3.10    Intersection Computed Lane Table
mapComputedLaneTable OBJECT-TYPE
    SYNTAX SEQUENCE OF MapComputedLaneEntry 
    MAX-ACCESS not-accessible
    STATUS deprecated
    DESCRIPTION "<Definition> This table contains computed lane information for an intersection. The number of rows in this table is equal to the maxComputedLanes object.
    <TableType> static
    <Object Identifier> 1.3.6.1.4.1.1206.4.2.17.2.10"
    ::= { map 10 }

mapComputedLaneEntry OBJECT-TYPE
    SYNTAX MapComputedLaneEntry
    MAX-ACCESS not-accessible
    STATUS deprecated
    DESCRIPTION "<Definition> The parameters for a specific computed lane at an intersection.
    <Object Identifier> 1.3.6.1.4.1.1206.4.2.17.2.10.1"
    INDEX  { mapLaneIndex }
    ::= { mapComputedLaneTable 1 }

MapComputedLaneEntry::= SEQUENCE {
    mapComputedLaneReference    INTEGER, --deprecated
    mapComputedLaneXOffset      INTEGER, --deprecated
    mapComputedLaneYOffset      INTEGER, --deprecated
    mapComputedLaneAngle        INTEGER, --deprecated
    mapComputedLaneXScale       INTEGER, --deprecated
    mapComputedLaneYScale       INTEGER } --deprecated

--7.3.10.1  Computed Lane Reference
mapComputedLaneReference OBJECT-TYPE
    SYNTAX Integer32 (1..255)
    MAX-ACCESS read-only
    STATUS deprecated
    DESCRIPTION "<Definition> The index of the lane (mapLaneIndex) that this computed lane is based on. This value shall not exceed the maxLanes object value.
    <Object Identifier> 1.3.6.1.4.1.1206.4.2.17.2.10.1.1"
    ::= { mapComputedLaneEntry 1 }

--7.3.10.2  Computed Lane X Offset
mapComputedLaneXOffset OBJECT-TYPE
    SYNTAX INTEGER (-32767..32767)
    MAX-ACCESS read-write
    STATUS deprecated
    DESCRIPTION "<Definition> For NTCIP 1202 user clarification, the X offset from the x-coordinate of the initial path node of the referenced lane (mapComputedLaneReference).
    <Object Identifier> 1.3.6.1.4.1.1206.4.2.17.2.10.1.2"
    REFERENCE "SAE J2735 DF_ComputedLane and DE_DrivenLineOffsetLg"
    DEFVAL { 0 }
    ::= { mapComputedLaneEntry 2 }

--7.3.10.3  Computed Lane Y Offset
mapComputedLaneYOffset OBJECT-TYPE
    SYNTAX INTEGER (-32767..32767)
    MAX-ACCESS read-write
    STATUS deprecated
    DESCRIPTION "<Definition> For NTCIP 1202 user clarification, the Y offset from the y-coordinate of the initial path node of the referenced lane (mapComputedLaneReference).
    <Object Identifier> 1.3.6.1.4.1.1206.4.2.17.2.10.1.3"
    REFERENCE "SAE J2735 DF_ComputedLane and DE_DrivenLineOffsetLarge"
    DEFVAL { 0 }
    ::= { mapComputedLaneEntry 3 }

--7.3.10.4  Computed Lane Angle
mapComputedLaneAngle OBJECT-TYPE
    SYNTAX Integer32 (0..28800)
    MAX-ACCESS read-write
    STATUS deprecated
    DESCRIPTION "<Definition> For NTCIP 1202 user clarification, a path rotation value for the lane. Rotation occurs around the initial path node of the referenced lane (mapComputedLaneReference).
    <Object Identifier> 1.3.6.1.4.1.1206.4.2.17.2.10.1.4"
    REFERENCE "SAE J2735 DF_ComputedLane and DE_Angle"
    DEFVAL { 28800 }
    ::= { mapComputedLaneEntry 4 }

--7.3.10.5  Computed Lane X Scale
mapComputedLaneXScale OBJECT-TYPE
    SYNTAX INTEGER (-2048..2047)
    MAX-ACCESS read-write
    STATUS deprecated
    DESCRIPTION "<Definition> For NTCIP 1202 user clarification, a value for translations or zooming of the lane's path nodes. The values found in the reference lane are all expanded or contracted based on the path node's X values from the coordinates of the reference lane's initial path point.
    <Object Identifier> 1.3.6.1.4.1.1206.4.2.17.2.10.1.5"
    REFERENCE "SAE J2735 DF_ComputedLane and DE_Scale_B12"
    DEFVAL { 0 }
    ::= { mapComputedLaneEntry 5 }

--7.3.10.6  Computed Lane Y Scale
mapComputedLaneYScale OBJECT-TYPE
    SYNTAX INTEGER(-2048..2047)
    MAX-ACCESS read-write
    STATUS deprecated
    DESCRIPTION "<Definition> For NTCIP 1202 user clarification, a value for translations or zooming of the lane's path nodes. The values found in the reference lane are all expanded or contracted based on the path node's Y values from the coordinates of the reference lane's initial path point.
    <Object Identifier> 1.3.6.1.4.1.1206.4.2.17.2.10.1.6"
    REFERENCE "SAE J2735 DF_ComputedLane and DE_Scale_B12"
    DEFVAL { 0 }
    ::= { mapComputedLaneEntry 6 }

--7.3.11    Maximum Lane Connections
maxLaneConnects OBJECT-TYPE
    SYNTAX Integer32 (0..16) 
    MAX-ACCESS read-only
    STATUS deprecated
    DESCRIPTION "<Definition> This object contains the maximum number of connections this RSU supports for a lane. This object indicates the maximum rows which shall appear in the mapLaneConnectTable object.
    <Object Identifier> 1.3.6.1.4.1.1206.4.2.17.2.11" 
    ::= { map 11 }

--7.3.12    Lane Connection Table
mapLaneConnectTable OBJECT-TYPE
    SYNTAX SEQUENCE OF MapLaneConnectEntry 
    MAX-ACCESS not-accessible
    STATUS deprecated
    DESCRIPTION "<Definition> This table contains the connection information for a lane beyond the stop line. The number of rows in this table is equal to the maxLaneConnects object.
    <TableType> static
    <Object Identifier> 1.3.6.1.4.1.1206.4.2.17.2.12"
    ::= { map 12 }

mapLaneConnectEntry OBJECT-TYPE
    SYNTAX MapLaneConnectEntry
    MAX-ACCESS not-accessible
    STATUS deprecated
    DESCRIPTION "<Definition> The parameters for a specific connection for a lane.
    <Object Identifier> 1.3.6.1.4.1.1206.4.2.17.2.12.1"
    INDEX  { mapLaneIndex, mapLaneConnectIndex }
    ::= { mapLaneConnectTable 1 }

MapLaneConnectEntry::= SEQUENCE {
    mapLaneConnectIndex                 INTEGER,--deprecated
    mapLaneConnectId                    INTEGER,--deprecated
    mapLaneConnectManeuver              INTEGER,--deprecated
    mapLaneConnectIntersectionId        INTEGER,--deprecated
    mapLaneConnectIntersectionAuthority INTEGER,--deprecated
    mapLaneConnectChannel               INTEGER,--deprecated
    mapLaneConnectClass                 INTEGER,--deprecated
    mapLaneConnectManeuverNumber        INTEGER } --deprecated

--7.3.12.1  Lane Connect Index
mapLaneConnectIndex OBJECT-TYPE
    SYNTAX Integer32 (1..16)
    UNITS "lane connection"
    MAX-ACCESS not-accessible
    STATUS deprecated
    DESCRIPTION "<Definition> The lane connection number for the objects in this row. This value shall not exceed the maxLaneConnects object value.
    <Object Identifier> 1.3.6.1.4.1.1206.4.2.17.2.12.1.1"
    ::= { mapLaneConnectEntry 1 }

--7.3.12.2  Lane Connect Identifier
mapLaneConnectId OBJECT-TYPE
    SYNTAX Integer32 (1..255)
    MAX-ACCESS read-only
    STATUS deprecated
    DESCRIPTION "<Definition> The index of the lane (mapLaneIndex) that this lane connects to. This value shall not exceed the maxLanes object value.
    <Object Identifier> 1.3.6.1.4.1.1206.4.2.17.2.12.1.2"
    ::= { mapLaneConnectEntry 2 }

--7.3.12.3  Lane Connect Maneuver
mapLaneConnectManeuver OBJECT-TYPE
    SYNTAX Integer32 (0..4095)
    MAX-ACCESS read-write
    STATUS deprecated
    DESCRIPTION "<Definition> For NTCIP 1202 user clarification, represents the maneuver(s) necessary from this lane at the stop line to the connecting lane. Note: these values may be further restricted by vehicle class, local regulations or other changing conditions. If a specific attribute for the lane is true, the associated bit shall be set to (1).
    <Object Identifier> 1.3.6.1.4.1.1206.4.2.17.2.12.1.3"
    REFERENCE "SAE J2735 DF_ConnectingLane and DE_AllowedManeuvers"
    ::= { mapLaneConnectEntry 3 }

--7.3.12.4  Lane Connect Remote Intersection ID
mapLaneConnectIntersectionId OBJECT-TYPE
    SYNTAX Integer32 (1..65535)
    MAX-ACCESS read-only
    STATUS deprecated
    DESCRIPTION "<Definition> For NTCIP 1202 user clarification, the identifier of the intersection if the connecting lane belongs to another intersection layout.
    <Object Identifier> 1.3.6.1.4.1.1206.4.2.17.2.12.1.4"
    REFERENCE "SAE J2735 DF_Connection and DE_IntersectionID"
    ::= { mapLaneConnectEntry 4 }

--7.3.12.5  Lane Connect Authority Identifier
mapLaneConnectIntersectionAuthority OBJECT-TYPE
    SYNTAX Integer32 (0..65535)
    MAX-ACCESS read-write
    STATUS deprecated
    DESCRIPTION "<Definition> For NTCIP 1202 user clarification, non zero if the intersection of the connecting lane belongs to another entity. A globally unique identifier assigned to an entity in a region (or country) responsible for assigning the intersectionId.
    <Object Identifier> 1.3.6.1.4.1.1206.4.2.17.2.12.1.5"
    REFERENCE "SAE J2735 DE_RoadRegulatorID"
    ::= { mapLaneConnectEntry 5 }

--7.3.12.6  Lane Connect Channel
mapLaneConnectChannel OBJECT-TYPE
    SYNTAX Integer32 (1..255)
    MAX-ACCESS read-write
    STATUS deprecated
    DESCRIPTION "<Definition> For NTCIP 1202 user clarification, the channelNumber that this lane connecting maneuver is associated with. This value shall not exceed the maxChannels object value.
    <Object Identifier> 1.3.6.1.4.1.1206.4.2.17.2.12.1.6"
    REFERENCE "SAE J2735 DF_Connection and DE_SignalGroupID"
    ::= { mapLaneConnectEntry 6 }

--7.3.12.7  Lane Connect Restriction Class
mapLaneConnectClass OBJECT-TYPE
    SYNTAX Integer32 (0..255)
    MAX-ACCESS read-write
    STATUS deprecated
    DESCRIPTION "<Definition> For NTCIP 1202 user clarification, the mapUserClassId to which this lane connection maneuver applies. A value of zero indicates that lane connection maneuver applies to all vehicle types.
    <Object Identifier> 1.3.6.1.4.1.1206.4.2.17.2.12.1.7"
    REFERENCE "SAE J2735 DF_Connection and DE_RestrictionClassID"
    DEFVAL { 0 }
    ::= { mapLaneConnectEntry 7 }

--7.3.12.8  Lane Connect Maneuver Number
mapLaneConnectManeuverNumber OBJECT-TYPE
    SYNTAX Integer32 (0..255)
    MAX-ACCESS read-only
    STATUS deprecated
    DESCRIPTION "<Definition> For NTCIP 1202 user clarification, the movementManeuverId for a lane to lane connection that this mapLaneIndex and mapLaneConnectIndex is tied to. The movementManeuverIdentifier is unique within the intersection. Used to relate this lane connection to variable interval information that may be sent in the SPAT message. A value of zero indicates undefined or not used.
    <Object Identifier> 1.3.6.1.4.1.1206.4.2.17.2.12.1.8"  
    REFERENCE "SAE J2735 DF_Connection and DE_LaneConnectionID"
    ::= { mapLaneConnectEntry 8 }

--7.3.13    Maximum Number of Speed Limits
maxSpeedLimits OBJECT-TYPE
    SYNTAX Integer32 (1..9)
    UNITS "speed limit"
    MAX-ACCESS read-only
    STATUS deprecated
    DESCRIPTION "<Definition> This object contains the maximum number of speed limit entries this CU supports. This object indicates the maximum rows which shall appear in the mapSpeedLimitTable object.
    <Object Identifier> 1.3.6.1.4.1.1206.4.2.17.2.13"
    ::= { map 13 }

--7.3.14    Intersection Speed Limit Table
mapSpeedLimitTable OBJECT-TYPE
    SYNTAX SEQUENCE OF MapSpeedLimitEntry 
    MAX-ACCESS not-accessible
    STATUS deprecated
    DESCRIPTION "<Definition> This table contains speed limit information. The number of rows in this table is equal to the maxSpeedLimits object.
    <TableType> static
    <Object Identifier> 1.3.6.1.4.1.1206.4.2.17.2.14"
    ::= { map 14 }

mapSpeedLimitEntry OBJECT-TYPE
    SYNTAX MapSpeedLimitEntry
    MAX-ACCESS not-accessible
    STATUS deprecated
    DESCRIPTION "<Definition> The parameters for a specific speed limit.
    <Object Identifier> 1.3.6.1.4.1.1206.4.2.17.2.14.1"
    INDEX  { mapSpeedLimitIndex }
    ::= { mapSpeedLimitTable 1 }


MapSpeedLimitEntry::= SEQUENCE {
    mapSpeedLimitIndex  INTEGER, --deprecated
    mapSpeedLimitType   INTEGER, --deprecated
    mapSpeedLimit       INTEGER } --deprecated

--7.3.14.1  Speed Limit Index
mapSpeedLimitIndex OBJECT-TYPE
    SYNTAX Integer32 (1..9)
    UNITS "speed limit"
    MAX-ACCESS not-accessible
    STATUS deprecated
    DESCRIPTION "<Definition> The speed limit index for objects in this row. This value shall not exceed the maxSpeedLimits object value.
    <Object Identifier> 1.3.6.1.4.1.1206.4.2.17.2.14.1.1"
    ::= { mapSpeedLimitEntry 1 }

--7.3.14.2  Speed Limit Type
mapSpeedLimitType OBJECT-TYPE
    SYNTAX INTEGER { unknown (0),                                    -- Speed limit type not available 
                 maxSpeedInSchoolZone (1),                       -- Only sent when the limit is active 
                 maxSpeedInSchoolZoneWhenChildrenArePresent (2), -- Sent at any time 
                 maxSpeedInConstructionZone (3),                 -- Used for work zones, incident zones, etc. where a reduced speed is present 
                 vehicleMinSpeed (4), 
                 vehicleMaxSpeed (5),                            -- Regulatory speed limit for general traffic 
                 vehicleNightMaxSpeed (6), 
                 truckMinSpeed (7), 
                 truckMaxSpeed (8), 
                 truckNightMaxSpeed (9), 
                 vehiclesWithTrailersMinSpeed (10), 
                 vehiclesWithTrailersMaxSpeed (11), 
                 vehiclesWithTrailersNightMaxSpeed (12) }
    MAX-ACCESS read-write
    STATUS deprecated
    DESCRIPTION "<Definition> For NTCIP 1202 user clarification, the first enumeration (0) is unknown, the second enumeration (1) is maxSpeedInSchoolZone, etc.
    <Object Identifier> 1.3.6.1.4.1.1206.4.2.17.2.14.1.2"
    REFERENCE "SAE J2735 DE_SpeedLimitType"
    DEFVAL { unknown }
    ::= { mapSpeedLimitEntry 2 }

--7.3.14.3  Speed Limit
mapSpeedLimit OBJECT-TYPE
    SYNTAX Integer32 (0..8191)
    MAX-ACCESS read-write
    STATUS deprecated
    DESCRIPTION "<Definition> For NTCIP 1202 user clarification, the speed limit value.
    <Object Identifier> 1.3.6.1.4.1.1206.4.2.17.2.14.1.3"
    REFERENCE "SAE J2735 DF_RegulatorySpeedLimit and DE_Velocity"
    DEFVAL { 8191 }
    ::= { mapSpeedLimitEntry 3 }

--7.3.15    Maximum User Types
maxUserTypes OBJECT-TYPE
    SYNTAX Integer32 (1..254)
    UNITS "user type"
    MAX-ACCESS read-only
    STATUS deprecated
    DESCRIPTION "<Definition> This object contains the maximum number of user type entries this CU supports. This object indicates the maximum rows which shall appear in the mapUserTable object.
    <Object Identifier> 1.3.6.1.4.1.1206.4.2.17.2.15"
    ::= { map 15 }

--7.3.16    Intersection User Types Table
mapUserTable OBJECT-TYPE
    SYNTAX SEQUENCE OF MapUserEntry 
    MAX-ACCESS not-accessible
    STATUS deprecated
    DESCRIPTION "<Definition> This table contains a list of user classes that belong to a given assigned index. The number of rows in this table is equal to the maxUserTypes object.
    <TableType> static
    <Object Identifier> 1.3.6.1.4.1.1206.4.2.17.2.16"
    ::= { map 16 }

mapUserEntry OBJECT-TYPE
    SYNTAX MapUserEntry
    MAX-ACCESS not-accessible
    STATUS deprecated
    DESCRIPTION "<Definition> A description of user type special movements supported at this intersection.
    <Object Identifier> 1.3.6.1.4.1.1206.4.2.17.2.16.1"
    INDEX  { mapUserIndex }
    ::= { mapUserTable 1 }

MapUserEntry::= SEQUENCE {
    mapUserIndex        INTEGER,        --deprecated
    mapUserClassTypes   OCTET STRING }  --deprecated

--7.3.16.1  MAP User Type Index
mapUserIndex OBJECT-TYPE
    SYNTAX Integer32 (1..254)
    MAX-ACCESS not-accessible
    STATUS deprecated
    DESCRIPTION "<Definition> For NTCIP 1202 user clarification, the index of the user type for objects in this row. This value shall not exceed the maxUserTypes object value.
    <Object Identifier> 1.3.6.1.4.1.1206.4.2.17.2.16.1.1"
    REFERENCE "SAE J2735 DE_RestrictionClassID"
    ::= { mapUserEntry 1 }

--7.3.16.2  MAP User Class Types
mapUserClassTypes OBJECT-TYPE
    SYNTAX OCTET STRING (SIZE (1..16))
    MAX-ACCESS read-write
    STATUS deprecated
    DESCRIPTION "<Definition> For NTCIP 1202 user clarification, each octet within the octet string represents an enumeration defined in SAE J2735 DF_RestrictionAppliesTo. This object is used to indicate movements at an intersection are intended for specific traveler types or classes, as represented by SAE J2735 DF_RestrictionAppliesTo.
    <Object Identifier> 1.3.6.1.4.1.1206.4.2.17.2.16.1.2"
    REFERENCE "SAE J2735 DF_RestrictionUserTypeList"
    DEFVAL { '00'H }
    ::= { mapUserEntry 2 }


--7.3.17    Maximum MAP Plans
maxMapPlans OBJECT-TYPE
SYNTAX Integer32 (0..8)
UNITS "map plan"
MAX-ACCESS read-only
STATUS deprecated
DESCRIPTION "<Definition> This object contains the maximum number of MAP plans this RSU supports. This object indicates the maximum rows which shall appear in the mapPlanTable object. Each MAP plan defines the lane indexes that are to be broadcasted in a MAP data message.
<Object Identifier> 1.3.6.1.4.1.1206.4.2.17.2.17"
::= { map 19 }

--7.3.18    MAP Plan Table
mapPlanTable OBJECT-TYPE
SYNTAX SEQUENCE OF MapPlanEntry 
MAX-ACCESS not-accessible
STATUS deprecated
DESCRIPTION "<Definition> This table contains MAP plans that are stored on this RSU for broadcast. The number of rows in this table is equal to the maxMapPlans object.
<TableType> static
<Object Identifier> 1.3.6.1.4.1.1206.4.2.17.2.18"
::= { map 20 }

mapPlanEntry OBJECT-TYPE
SYNTAX MapPlanEntry
MAX-ACCESS not-accessible
STATUS deprecated
DESCRIPTION "<Definition> The lane indexes that are to be broadcasted by a RSU.
<Object Identifier> 1.3.6.1.4.1.1206.4.2.17.2.18.1"
INDEX  { mapPlanIndex }
::= { mapPlanTable 1 }

MapPlanEntry::= SEQUENCE {
    mapPlanIndex            INTEGER,        --deprecated
    mapPlanLanes            OCTET STRING,   --deprecated
    mapPlanCRC              OCTET STRING,   --deprecated
    mapPlanLayerType        INTEGER,        --deprecated
    mapPlanLayerId          INTEGER,        --deprecated
    mapPlanMetadataMethod   DisplayString,  --deprecated
    mapPlanMetadataAgency   DisplayString,  --deprecated
    mapPlanMetadataDate     DisplayString,  --deprecated
    mapPlanMetadataGeoid    DisplayString } --deprecated

--7.3.18.1  MAP Plan Index
mapPlanIndex OBJECT-TYPE
    SYNTAX Integer32 (1..255)
    UNITS "number"
    MAX-ACCESS not-accessible
    STATUS deprecated
    DESCRIPTION "<Definition> The index of the MAP plan number for objects in this row. This value shall not exceed the maxMapPlans object value. Each MAP plan defines the lane indexes that are to be broadcasted in a MAP data message.
    <Object Identifier> 1.3.6.1.4.1.1206.4.2.17.2.18.1.1"
    ::= { mapPlanEntry 1 }

--7.3.18.2  MAP Plan Lanes
mapPlanLanes OBJECT-TYPE
    SYNTAX OCTET STRING
    MAX-ACCESS read-write
    STATUS deprecated
    DESCRIPTION "<Definition> Each octet within the octet string contains the mapLaneIndex (binary value) that is to be broadcasted in a MAP data message. An octet of 00 indicates there are no additional lane indexes in the sequence.
    <Object Identifier> 1.3.6.1.4.1.1206.4.2.17.2.18.1.2"
    DEFVAL { ''H }
    ::= { mapPlanEntry 2 }

--7.3.18.3  MAP Plan CRC
mapPlanCRC OBJECT-TYPE
    SYNTAX OCTET STRING (SIZE(2))
    MAX-ACCESS read-only
    STATUS deprecated
    DESCRIPTION "<Definition> The mapPlanCRC is calculated using the CRC-16
        defined in ISO/IEC 13239:2002) using the associated OER-encoded (as
        defined in NTCIP 1102) MapPlanCRCByteStream.

        MapPlanCRCByteStream ::= SEQUENCE OF MapPlanCRCList
 
        mapPlanCRCList  SEQUENCE { 
            mapLaneCRC      INTEGER (1..65535) }
 
        For example, if there are three lanes referenced in mapPlanLanes,
        resulting in the value of mapPlanLanes being 08 04 05 00, and
        mapLaneCRC.8 is 42 73, mapLaneCRC.4 is 22 16, and mapLaneCRC.5 is
        97 63, then the OER-encoded string on which the CRC shall be
        calculated is:
            01 03 42 73 22 16 97 63

    <Object Identifier> 1.3.6.1.4.1.1206.4.2.17.2.18.1.3"
    DEFVAL { '0000'H }
    ::= { mapPlanEntry 3 }

--7.3.18.4  MAP Plan Layer Type
mapPlanLayerType OBJECT-TYPE
    SYNTAX INTEGER {none (0), 
                mixedContent (1), -- two or more of the below types 
                generalMapData (2), 
                intersectionData (3), 
                curveData (4),
                roadwaySectionData (5), 
                parkingAreaData (6), 
                sharedLaneData (7) }
    MAX-ACCESS read-write
    STATUS deprecated
    DESCRIPTION "<Definition> For NTCIP 1202 user clarification, the enumerations for this object is defined in SAE J2735 DE_LayerType, where 0 is none, 1 is mixedContent, etc.
    <Object Identifier> 1.3.6.1.4.1.1206.4.2.17.2.18.1.4"
    REFERENCE "SAE J2735 DE_LayerType"
    ::= { mapPlanEntry 4 }

--7.3.18.5  MAP Plan Layer Identifier
mapPlanLayerId OBJECT-TYPE
    SYNTAX Integer32 (0..100)
    MAX-ACCESS read-write
    STATUS deprecated
    DESCRIPTION "<Definition> For NTCIP 1202 user clarification, an identifier for a layer of a geographic map fragment, such as an intersection.
    <Object Identifier> 1.3.6.1.4.1.1206.4.2.17.2.18.1.5"
    REFERENCE "SAE J2735 DE_LayerID"
    ::= { mapPlanEntry 5 }

--7.3.18.6  MAP Plan Metadata Method
mapPlanMetadataMethod OBJECT-TYPE
    SYNTAX DisplayString (SIZE (0..255))
    MAX-ACCESS read-write
    STATUS deprecated
    DESCRIPTION "<Definition> For NTCIP 1202 user clarification, this object contains a description of the method used to process the map fragment being broadcast in the MAP data message.
    <Object Identifier> 1.3.6.1.4.1.1206.4.2.17.2.18.1.6"
    REFERENCE "SAE J2735 DF_DataParameters"
    ::= { mapPlanEntry 6 }

--7.3.18.7  MAP Plan Metadata Agency
mapPlanMetadataAgency OBJECT-TYPE
    SYNTAX DisplayString (SIZE (0..255))
    MAX-ACCESS read-write
    STATUS deprecated
    DESCRIPTION "<Definition> For NTCIP 1202 user clarification, this object describes the agency that developed or processed the map fragment being broadcast in the MAP data message.
    <Object Identifier> 1.3.6.1.4.1.1206.4.2.17.2.18.1.7"
    REFERENCE "SAE J2735 DF_DataParameters"
    ::= { mapPlanEntry 7 }

--7.3.18.8  MAP Plan Metadata Date
mapPlanMetadataDate OBJECT-TYPE
    SYNTAX DisplayString (SIZE (0..255))
    MAX-ACCESS read-write
    STATUS deprecated
    DESCRIPTION "<Definition> For NTCIP 1202 user clarification, this object contains the date that the map fragment being broadcast in the MAP data message was last checked.
    <Object Identifier> 1.3.6.1.4.1.1206.4.2.17.2.18.1.8"
    REFERENCE "SAE J2735 DF_DataParameters"
    ::= { mapPlanEntry 8 }

--7.3.18.9  MAP Plan Metadata Geoid
mapPlanMetadataGeoid OBJECT-TYPE
    SYNTAX DisplayString (SIZE (0..255))
    MAX-ACCESS read-write
    STATUS deprecated
    DESCRIPTION "<Object Identifier> 1.3.6.1.4.1.1206.4.2.17.2.18.1.9"
    REFERENCE "SAE J2735 DF_DataParameters"
    ::= { mapPlanEntry 9 }



END
